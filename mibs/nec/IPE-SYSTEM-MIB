--
-- ASN.1 MIB Definitions
-- Output Date: Tue Jul 12 15:00:32 2016
--

IPE-SYSTEM-MIB DEFINITIONS ::= BEGIN

-----------------------------------------------
-- IMPORTS Definitions
-----------------------------------------------

    IMPORTS
        BridgeId, Timeout
            FROM BRIDGE-MIB
        InterfaceIndex
            FROM IF-MIB
        Counter32, enterprises, Integer32, IpAddress, NOTIFICATION-TYPE,
        OBJECT-TYPE, Opaque
            FROM SNMPv2-SMI
        DateAndTime, DisplayString, MacAddress, RowStatus, TEXTUAL-CONVENTION
            FROM SNMPv2-TC;

-----------------------------------------------
-- Textual Convention Definitions
-----------------------------------------------

    AlarmTypeValue ::= TEXTUAL-CONVENTION
        STATUS       current
        DESCRIPTION  "Alarm Type (CCITT Rec. X.733)"
        SYNTAX       INTEGER {
                         invalid(0),
                         communicationsAlarm(1),
                         qualityOfServiceAlarm(2),
                         processingErrorAlarm(3),
                         equipmentAlarm(4),
                         environmentalAlarm(5),
                         integrityViolationAlarm(6),
                         operationalViolationAlarm(7),
                         physicalViolationAlarm(8),
                         securityViolationAlarm(9),
                         timeDomainViolationAlarm(10)
                     }

    ProbableCauseValue ::= TEXTUAL-CONVENTION
        STATUS       current
        DESCRIPTION  "Probable Cause (CCITT Rec. X.733)"
        SYNTAX       INTEGER {
                         invalid(0),
                         aIS(1),
                         callSetUpFailure(2),
                         degradedSignal(3),
                         farEndReceiverFailure(4),
                         framingError(5),
                         lossOfFrame(6),
                         lossOfPointer(7),
                         lossOfSignal(8),
                         payloadTypeMismatch(9),
                         transmissionError(10),
                         remoteAlarmInterface(11),
                         excessiveBER(12),
                         pathTraceMismatch(13),
                         unavailable(14),
                         signalLabelMismatch(15),
                         lossOfMultiFrame(16),
                         receiveFailure(17),
                         transmitFailure(18),
                         modulationFailure(19),
                         demodulationFailure(20),
                         broadcastChannelFailure(21),
                         connectionEstablishmentError(22),
                         invalidMessageReceived(23),
                         localNodeTransmissionError(24),
                         remoteNodeTransmissionError(25),
                         routingFailure(26),
                         backplaneFailure(51),
                         dataSetProblem(52),
                         equipmentIdentifierDuplication(53),
                         externalIFDeviceProblem(54),
                         lineCardProblem(55),
                         multiplexerProblem(56),
                         nEIdentifierDuplication(57),
                         powerProblem(58),
                         processorProblem(59),
                         protectionPathFailure(60),
                         receiverFailure(61),
                         replaceableUnitMissing(62),
                         replaceableUnitTypeMismatch(63),
                         synchronizationSourceMismatch(64),
                         terminalProblem(65),
                         timingProblem(66),
                         transmitterFailure(67),
                         trunkCardProblem(68),
                         replaceableUnitProblem(69),
                         realTimeClockFailure(70),
                         antennaFailure(71),
                         batteryChargingFailure(72),
                         diskFailure(73),
                         frequencyHoppingFailure(74),
                         iODeviceError(75),
                         lossOfSynchronisation(76),
                         lossOfRedundancy(77),
                         powerSupplyFailure(78),
                         signalQualityEvaluationFailure(79),
                         tranceiverFailure(80),
                         protectionMechanismFailure(81),
                         protectingResourceFailure(82),
                         airCompressorFailure(101),
                         airConditioningFailure(102),
                         airDryerFailure(103),
                         batteryDischarging(104),
                         batteryFailure(105),
                         commercialPowerFailure(106),
                         coolingFanFailure(107),
                         engineFailure(108),
                         fireDetectorFailure(109),
                         fuseFailure(110),
                         generatorFailure(111),
                         lowBatteryThreshold(112),
                         pumpFailure(113),
                         rectifierFailure(114),
                         rectifierHighVoltage(115),
                         rectifierLowFVoltage(116),
                         ventilationsSystemFailure(117),
                         enclosureDoorOpen(118),
                         explosiveGas(119),
                         fire(120),
                         flood(121),
                         highHumidity(122),
                         highTemperature(123),
                         highWind(124),
                         iceBuildUp(125),
                         intrusionDetection(126),
                         lowFuel(127),
                         lowHumidity(128),
                         lowCablePressure(129),
                         lowTemperatue(130),
                         lowWater(131),
                         smoke(132),
                         toxicGas(133),
                         coolingSystemFailure(134),
                         externalEquipmentFailure(135),
                         externalPointFailure(136),
                         storageCapacityProblem(151),
                         memoryMismatch(152),
                         corruptData(153),
                         outOfCPUCycles(154),
                         sfwrEnvironmentProblem(155),
                         sfwrDownloadFailure(156),
                         lossOfRealTimel(157),
                         applicationSubsystemFailure(158),
                         configurationOrCustomisationError(159),
                         databaseInconsistency(160),
                         fileError(161),
                         outOfMemory(162),
                         softwareError(163),
                         timeoutExpired(164),
                         underlayingResourceUnavailable(165),
                         versionMismatch(166),
                         bandwidthReduced(201),
                         congestion(202),
                         excessiveErrorRate(203),
                         excessiveResponseTime(204),
                         excessiveRetransmissionRate(205),
                         reducedLoggingCapability(206),
                         systemResourcesOverload(207),
                         adapterError(500),
                         applicationSubsystemFailture(501),
                         bandwidthReducedX733(502),
                         callEstablishmentError(503),
                         communicationsProtocolError(504),
                         communicationsSubsystemFailure(505),
                         configurationOrCustomizationError(506),
                         congestionX733(507),
                         coruptData(508),
                         cpuCyclesLimitExceeded(509),
                         dataSetOrModemError(510),
                         degradedSignalX733(511),
                         dteDceInterfaceError(512),
                         enclosureDoorOpenX733(513),
                         equipmentMalfunction(514),
                         excessiveVibration(515),
                         fileErrorX733(516),
                         fireDetected(517),
                         framingErrorX733(518),
                         heatingVentCoolingSystemProblem(519),
                         humidityUnacceptable(520),
                         inputOutputDeviceError(521),
                         inputDeviceError(522),
                         lanError(523),
                         leakDetected(524),
                         localNodeTransmissionErrorX733(525),
                         lossOfFrameX733(526),
                         lossOfSignalX733(527),
                         materialSupplyExhausted(528),
                         multiplexerProblemX733(529),
                         outOfMemoryX733(530),
                         ouputDeviceError(531),
                         performanceDegraded(532),
                         powerProblems(533),
                         pressureUnacceptable(534),
                         processorProblems(535),
                         pumpFailureX733(536),
                         queueSizeExceeded(537),
                         receiveFailureX733(538),
                         receiverFailureX733(539),
                         remoteNodeTransmissionErrorX733(540),
                         resourceAtOrNearingCapacity(541),
                         responseTimeExecessive(542),
                         retransmissionRateExcessive(543),
                         softwareErrorX733(544),
                         softwareProgramAbnormallyTerminated(545),
                         softwareProgramError(546),
                         storageCapacityProblemX733(547),
                         temperatureUnacceptable(548),
                         thresholdCrossed(549),
                         timingProblemX733(550),
                         toxicLeakDetected(551),
                         transmitFailureX733(552),
                         transmiterFailure(553),
                         underlyingResourceUnavailable(554),
                         versionMismatchX733(555),
                         authenticationFailure(600),
                         breachOfConfidentiality(601),
                         cableTamper(602),
                         delayedInformation(603),
                         denialOfService(604),
                         duplicateInformation(605),
                         informationMissing(606),
                         informationModificationDetected(607),
                         informationOutOfSequence(608),
                         keyExpired(609),
                         nonRepudiationFailure(610),
                         outOfHoursActivity(611),
                         outOfService(612),
                         proceduralError(613),
                         unauthorizedAccessAttempt(614),
                         unexpectedInformation(615),
                         other(1024)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    system1 OBJECT IDENTIFIER
        ::= { radioEquipment 1 }

    system5 OBJECT IDENTIFIER
        ::= { radioEquipment 5 }

-----------------------------------------------
-- system1 Group Definitions
-----------------------------------------------

    pmSystem OBJECT IDENTIFIER
        ::= { system1 1 }

    sysPmType OBJECT-TYPE
        SYNTAX       INTEGER { typeBranchNE(13), typeNormal(14) }
        MAX-ACCESS   read-only
        STATUS       current
        DESCRIPTION  "PM TYPE SETTING."
        ::= { pmSystem 3 }

    sysPrimaryIpAddress OBJECT-TYPE
        SYNTAX       IpAddress
        MAX-ACCESS   read-only
        STATUS       current
        DESCRIPTION  "PRIMARY IP ADDRESS."
        ::= { pmSystem 5 }

    sysOppositeIpAddress OBJECT-TYPE
        SYNTAX       IpAddress
        MAX-ACCESS   read-only
        STATUS       current
        DESCRIPTION  "IP address of the destination."
        ::= { pmSystem 9 }

    sysEquipmentType OBJECT-TYPE
        SYNTAX       Integer32
        MAX-ACCESS   read-only
        STATUS       current
        DESCRIPTION  "Equipment Type."
        ::= { pmSystem 13 }

    sysEquipmentConfig OBJECT-TYPE
        SYNTAX       Integer32
        MAX-ACCESS   read-only
        STATUS       current
        DESCRIPTION  "Equipment Config."
        ::= { pmSystem 14 }

-----------------------------------------------
-- system5 Group Definitions
-----------------------------------------------

    ipeSystemGroup OBJECT IDENTIFIER
        ::= { system5 1 }

    ipeSysInfoTable OBJECT-TYPE
        SYNTAX       SEQUENCE OF IpeSysInfoEntry
        MAX-ACCESS   not-accessible
        STATUS       current
        DESCRIPTION  "Table of System Information."
        ::= { ipeSystemGroup 1 }

    ipeSysInfoEntry OBJECT-TYPE
        SYNTAX       IpeSysInfoEntry
        MAX-ACCESS   not-accessible
        STATUS       current
        DESCRIPTION  "Entry of System Information."
        INDEX        { ipeSysInfoIndex }
        ::= { ipeSysInfoTable 1 }

    IpeSysInfoEntry ::= SEQUENCE {
        ipeSysInfoIndex         Integer32,
        ipeSysInfoNEAddress     IpAddress,
        ipeSysNeName            DisplayString,
        ipeSysAreaName          DisplayString,
        ipeSysNote              DisplayString,
        ipeSysPrimaryIpAddress  IpAddress,
        ipeSysSubnetMask        IpAddress,
        ipeSysDefaultGateway    IpAddress,
        ipeSysMacAddress        MacAddress,
        ipeSysMibVersion        DisplayString,
        ipeSysEquipmentType     Integer32,
        ipeSysPmType            Integer32
    }

    ipeSysInfoIndex OBJECT-TYPE
        SYNTAX       Integer32 (1..1)
        MAX-ACCESS   not-accessible
        STATUS       current
        DESCRIPTION  "Index of this table."
        ::= { ipeSysInfoEntry 1 }

    ipeSysInfoNEAddress OBJECT-TYPE
        SYNTAX       IpAddress
        MAX-ACCESS   not-accessible
        STATUS       current
        DESCRIPTION  "reserved."
        ::= { ipeSysInfoEntry 2 }

    ipeSysNeName OBJECT-TYPE
        SYNTAX       DisplayString
        MAX-ACCESS   read-only
        STATUS       current
        DESCRIPTION  "Equipment name (for display)."
        ::= { ipeSysInfoEntry 3 }

    ipeSysAreaName OBJECT-TYPE
        SYNTAX       DisplayString
        MAX-ACCESS   read-only
        STATUS       current
        DESCRIPTION  "Area name (for display)."
        ::= { ipeSysInfoEntry 4 }

    ipeSysNote OBJECT-TYPE
        SYNTAX       DisplayString
        MAX-ACCESS   read-only
        STATUS       current
        DESCRIPTION  "Memorandum (for display)."
        ::= { ipeSysInfoEntry 5 }

    ipeSysPrimaryIpAddress OBJECT-TYPE
        SYNTAX       IpAddress
        MAX-ACCESS   read-write
        STATUS       current
        DESCRIPTION  "Primary IP Address (for display and setting)."
        ::= { ipeSysInfoEntry 6 }

    ipeSysSubnetMask OBJECT-TYPE
        SYNTAX       IpAddress
        MAX-ACCESS   read-only
        STATUS       current
        DESCRIPTION  "Subnet mask (for display)."
        ::= { ipeSysInfoEntry 7 }

    ipeSysDefaultGateway OBJECT-TYPE
        SYNTAX       IpAddress
        MAX-ACCESS   read-only
        STATUS       current
        DESCRIPTION  "Default gateway (for display)."
        ::= { ipeSysInfoEntry 8 }

    ipeSysMacAddress OBJECT-TYPE
        SYNTAX       MacAddress
        MAX-ACCESS   read-only
        STATUS       current
        DESCRIPTION  "MAC address (for display)."
        ::= { ipeSysInfoEntry 9 }

    ipeSysMibVersion OBJECT-TYPE
        SYNTAX       DisplayString
        MAX-ACCESS   read-only
        STATUS       current
        DESCRIPTION  "MIB version."
        ::= { ipeSysInfoEntry 10 }

    ipeSysEquipmentType OBJECT-TYPE
        SYNTAX       Integer32
        MAX-ACCESS   read-only
        STATUS       current
        DESCRIPTION  "Equipment type."
        ::= { ipeSysInfoEntry 11 }

    ipeSysPmType OBJECT-TYPE
        SYNTAX       Integer32 (1..20)
        MAX-ACCESS   read-write
        STATUS       current
        DESCRIPTION  
            "Number of Branch.
            1=normalNE mode.
            1!=branchNE mode (2<= ipeSysPmType <= 20)."
        ::= { ipeSysInfoEntry 12 }

    ipeSysInventoryInfoTable OBJECT-TYPE
        SYNTAX       SEQUENCE OF IpeSysInventoryInfoEntry
        MAX-ACCESS   not-accessible
        STATUS       current
        DESCRIPTION  "Table of system basic information."
        ::= { ipeSystemGroup 2 }

    ipeSysInventoryInfoEntry OBJECT-TYPE
        SYNTAX       IpeSysInventoryInfoEntry
        MAX-ACCESS   not-accessible
        STATUS       current
        DESCRIPTION  "Entry of system basic information."
        INDEX        { ipeSysInventoryInfoIndex }
        ::= { ipeSysInventoryInfoTable 1 }

    IpeSysInventoryInfoEntry ::= SEQUENCE {
        ipeSysInventoryInfoIndex         Integer32,
        ipeSysInventoryInfoNEAddress     IpAddress,
        ipeSysInvSoftwareVersion         DisplayString,
        ipeSysInvSoftwareReleaseDate     DateAndTime,
        ipeSysInvDlSoftwareVersion       DisplayString,
        ipeSysInvOperationSide           Integer32,
        ipeSysInvStandbySoftwareVersion  DisplayString
    }

    ipeSysInventoryInfoIndex OBJECT-TYPE
        SYNTAX       Integer32 (1..1)
        MAX-ACCESS   not-accessible
        STATUS       current
        DESCRIPTION  "Index of this table."
        ::= { ipeSysInventoryInfoEntry 1 }

    ipeSysInventoryInfoNEAddress OBJECT-TYPE
        SYNTAX       IpAddress
        MAX-ACCESS   not-accessible
        STATUS       current
        DESCRIPTION  "reserved."
        ::= { ipeSysInventoryInfoEntry 2 }

    ipeSysInvSoftwareVersion OBJECT-TYPE
        SYNTAX       DisplayString
        MAX-ACCESS   read-only
        STATUS       current
        DESCRIPTION  "Software version."
        ::= { ipeSysInventoryInfoEntry 3 }

    ipeSysInvSoftwareReleaseDate OBJECT-TYPE
        SYNTAX       DateAndTime
        MAX-ACCESS   read-only
        STATUS       current
        DESCRIPTION  "Software update date and time."
        ::= { ipeSysInventoryInfoEntry 4 }

    ipeSysInvDlSoftwareVersion OBJECT-TYPE
        SYNTAX       DisplayString
        MAX-ACCESS   read-only
        STATUS       current
        DESCRIPTION  "Download control."
        ::= { ipeSysInventoryInfoEntry 5 }

    ipeSysInvOperationSide OBJECT-TYPE
        SYNTAX       Integer32
        MAX-ACCESS   read-only
        STATUS       current
        DESCRIPTION  "Active side information."
        ::= { ipeSysInventoryInfoEntry 6 }

    ipeSysInvStandbySoftwareVersion OBJECT-TYPE
        SYNTAX       DisplayString
        MAX-ACCESS   read-only
        STATUS       current
        DESCRIPTION  "Firmware version of inactive side."
        ::= { ipeSysInventoryInfoEntry 7 }

    ipeSysOperationGroup OBJECT IDENTIFIER
        ::= { ipeSystemGroup 3 }

    ipeSysOpTimeTable OBJECT-TYPE
        SYNTAX       SEQUENCE OF IpeSysOpTimeEntry
        MAX-ACCESS   not-accessible
        STATUS       current
        DESCRIPTION  "Table of date and time."
        ::= { ipeSysOperationGroup 1 }

    ipeSysOpTimeEntry OBJECT-TYPE
        SYNTAX       IpeSysOpTimeEntry
        MAX-ACCESS   not-accessible
        STATUS       current
        DESCRIPTION  "Entry of date and time."
        INDEX        { ipeSysOpTimeIndex }
        ::= { ipeSysOpTimeTable 1 }

    IpeSysOpTimeEntry ::= SEQUENCE {
        ipeSysOpTimeIndex      Integer32,
        ipeSysOpTimeNEAddress  IpAddress,
        ipeSysOpCurrentTime    DateAndTime,
        ipeSysOpStartTime      DateAndTime,
        ipeSysOpUpTime         Counter32
    }

    ipeSysOpTimeIndex OBJECT-TYPE
        SYNTAX       Integer32 (1..1)
        MAX-ACCESS   not-accessible
        STATUS       current
        DESCRIPTION  "Index of this table."
        ::= { ipeSysOpTimeEntry 1 }

    ipeSysOpTimeNEAddress OBJECT-TYPE
        SYNTAX       IpAddress
        MAX-ACCESS   not-accessible
        STATUS       current
        DESCRIPTION  "reserved."
        ::= { ipeSysOpTimeEntry 2 }

    ipeSysOpCurrentTime OBJECT-TYPE
        SYNTAX       DateAndTime
        MAX-ACCESS   read-write
        STATUS       current
        DESCRIPTION  "Current time."
        ::= { ipeSysOpTimeEntry 3 }

    ipeSysOpStartTime OBJECT-TYPE
        SYNTAX       DateAndTime
        MAX-ACCESS   read-only
        STATUS       current
        DESCRIPTION  "OS started time."
        ::= { ipeSysOpTimeEntry 4 }

    ipeSysOpUpTime OBJECT-TYPE
        SYNTAX       Counter32
        MAX-ACCESS   read-only
        STATUS       current
        DESCRIPTION  "Duration after OS started (second)."
        ::= { ipeSysOpTimeEntry 5 }

    ipeSysOpFileDownloadTable OBJECT-TYPE
        SYNTAX       SEQUENCE OF IpeSysOpFileDownloadEntry
        MAX-ACCESS   not-accessible
        STATUS       current
        DESCRIPTION  "Table of file download."
        ::= { ipeSysOperationGroup 2 }

    ipeSysOpFileDownloadEntry OBJECT-TYPE
        SYNTAX       IpeSysOpFileDownloadEntry
        MAX-ACCESS   not-accessible
        STATUS       current
        DESCRIPTION  "Entry of file download."
        INDEX        { ipeSysOpFileDownloadIndex }
        ::= { ipeSysOpFileDownloadTable 1 }

    IpeSysOpFileDownloadEntry ::= SEQUENCE {
        ipeSysOpFileDownloadIndex           Integer32,
        ipeSysOpFileDownloadNEAddress       IpAddress,
        ipeSysOpFileDownloadModule          INTEGER,
        ipeSysOpFileDownloadCpuResetDetail  INTEGER,
        ipeSysOpFileDownloadStatus          INTEGER,
        ipeSysOpFileDownloadCtrl            INTEGER,
        ipeSysOpFileDownloadProtocolType    INTEGER
    }

    ipeSysOpFileDownloadIndex OBJECT-TYPE
        SYNTAX       Integer32 (1..1)
        MAX-ACCESS   not-accessible
        STATUS       current
        DESCRIPTION  "Index of this table."
        ::= { ipeSysOpFileDownloadEntry 1 }

    ipeSysOpFileDownloadNEAddress OBJECT-TYPE
        SYNTAX       IpAddress
        MAX-ACCESS   not-accessible
        STATUS       current
        DESCRIPTION  "reserved."
        ::= { ipeSysOpFileDownloadEntry 2 }

    ipeSysOpFileDownloadModule OBJECT-TYPE
        SYNTAX       INTEGER {
                         invalid(0),
                         idu(1),
                         odu(2),
                         mdprm(3),
                         raFpga(4),
                         ipeFpga(5),
                         softkey(7),
                         cfgNet(8),
                         cfgEqu(9),
                         cfgUser(10),
                         https(11)
                     }
        MAX-ACCESS   read-only
        STATUS       current
        DESCRIPTION  
            "Program type. *'0:Invalidity' is used as an initial state."
        ::= { ipeSysOpFileDownloadEntry 3 }

    ipeSysOpFileDownloadCpuResetDetail OBJECT-TYPE
        SYNTAX       INTEGER { invalid(0), revertReset(1), normReset(2) }
        MAX-ACCESS   read-write
        STATUS       current
        DESCRIPTION  
            "CPU reset control.
            
            0:Invalidity
            1:revert reset
            2:normal reset( without revert )
            
            *'0:Invalidity' is used as an initial state."
        ::= { ipeSysOpFileDownloadEntry 4 }

    ipeSysOpFileDownloadStatus OBJECT-TYPE
        SYNTAX       INTEGER {
                         invalid(0),
                         downloadCompleted(1),
                         downloadFailed(2),
                         downloadExecuting(3),
                         downloadSuspending(4)
                     }
        MAX-ACCESS   read-only
        STATUS       current
        DESCRIPTION  
            "Download result.
            
            0:Invalidity
            1:Completed
            2:Failed
            3:Executing
            4:Suspending
            
            *'0:Invalidity' is used as an initial state.
            
            *A change state is the following three kinds.
            1)When it operates normally: 
              (Start)->(3:Executing)->(1:Completed)
            2)When it cancels on the way:
              (Start)->(3:Executing)->(4:Suspending)-> (Completed)
            3)When unusual detection is carried out on the way:
              (Start)->(3:Executing)->(2:Failed)
            
            *The download start from excluding (3:Executing) is permitted.
            *The download start from (3:Executing) is not permitted.
            
            *Pertinent details: ipeSysOpFileDownloadCtrl"
        ::= { ipeSysOpFileDownloadEntry 5 }

    ipeSysOpFileDownloadCtrl OBJECT-TYPE
        SYNTAX       INTEGER {
                         invalid(0),
                         startDownload(1),
                         suspendDownload(2),
                         startUpload(3),
                         endUpload(4),
                         resetDownload(5)
                     }
        MAX-ACCESS   read-write
        STATUS       current
        DESCRIPTION  
            "Download control.
            
            0:Invalidity
            1:Download start
            2:Download suspend
            3:Upload start
            4:Upload end
            5:Download reset
            
            *'0:Invalidity' is used as an initial state.
            *'5:Download reset' terminates the FTP server(vsftpd) with the
            deletion processing in the type of the file for all download
            directory.
            
            *The object file name allows only alphanumeric character '0-9',
            'a-z', 'A-Z' of ASCII code, and sign '-_.+'.
            
            *Pertinent details: ipeSysOpFileDownloadProtocolType
            *Pertinent details: ipeSysOpFileDownloadModule
            *Pertinent details: ipeSysOpFileDownloadStatus
            *Pertinent details: ipeFsUpdateFileStatus
            *Pertinent details: ipeFsUsbProcStatus
            
            [Race condition]
            *When ipeSysOpFileDownloadStatus is (3:Executing) or
            (4:Suspending), (1:Download start) is invalid.
            *When ipeSysOpFileDownloadStatus is (4:Suspending), (2:Download
            suspend) is invalid.
            *When ipeSysOpFileDownloadStatus is (0:Invalidity), (1:Download
            start) is valid, but do nothing.
            *When ipeFsUpdateFileStatusis(3:Executing), it is invalid. Other
            one is valid.
            *When ipeFsUsbProcStatus is (2:Normal:Process executing), it is
            invalid. Other one is valid.
            
            [Indispensable condition]
            *When it is  (1:Download start) or (3:Upload start), (4:Upload
            end),ipeSysOpFileDownloadProtocolType setup is indispensable."
        ::= { ipeSysOpFileDownloadEntry 6 }

    ipeSysOpFileDownloadProtocolType OBJECT-TYPE
        SYNTAX       INTEGER { invalid(0), ftp(1), sftp(2), http(3) }
        MAX-ACCESS   read-write
        STATUS       current
        DESCRIPTION  
            "Kind of protocol,
            
            *'0:Invalidity' is used as an initial state.
            
            *Pertinent details: ipeSysOpFileDownloadCtrl"
        ::= { ipeSysOpFileDownloadEntry 7 }

    ipeSysOpProgramPmonRmonClearTable OBJECT-TYPE
        SYNTAX       SEQUENCE OF IpeSysOpProgramPmonRmonClearEntry
        MAX-ACCESS   not-accessible
        STATUS       current
        DESCRIPTION  ""
        ::= { ipeSysOperationGroup 3 }

    ipeSysOpProgramPmonRmonClearEntry OBJECT-TYPE
        SYNTAX       IpeSysOpProgramPmonRmonClearEntry
        MAX-ACCESS   not-accessible
        STATUS       current
        DESCRIPTION  ""
        INDEX        { ipeSysOpProgramPmonRmonClearIndex }
        ::= { ipeSysOpProgramPmonRmonClearTable 1 }

    IpeSysOpProgramPmonRmonClearEntry ::= SEQUENCE {
        ipeSysOpProgramPmonRmonClearIndex      Integer32,
        ipeSysOpProgramPmonRmonClearNEAddress  IpAddress,
        ipeSysOpProgramPmonRmonClear           Integer32,
        ipeSysOpProgramPmonRmonClearResult     INTEGER
    }

    ipeSysOpProgramPmonRmonClearIndex OBJECT-TYPE
        SYNTAX       Integer32 (1..1)
        MAX-ACCESS   not-accessible
        STATUS       current
        DESCRIPTION  "Index of this table."
        ::= { ipeSysOpProgramPmonRmonClearEntry 1 }

    ipeSysOpProgramPmonRmonClearNEAddress OBJECT-TYPE
        SYNTAX       IpAddress
        MAX-ACCESS   not-accessible
        STATUS       current
        DESCRIPTION  "reserved."
        ::= { ipeSysOpProgramPmonRmonClearEntry 2 }

    ipeSysOpProgramPmonRmonClear OBJECT-TYPE
        SYNTAX       Integer32
        MAX-ACCESS   read-write
        STATUS       current
        DESCRIPTION  
            "PMON data clear control
            0:FIXED VALUE 1:REQUEST"
        ::= { ipeSysOpProgramPmonRmonClearEntry 3 }

    ipeSysOpProgramPmonRmonClearResult OBJECT-TYPE
        SYNTAX       INTEGER { invalid(0), completed(1), failed(2), executing(3) }
        MAX-ACCESS   read-only
        STATUS       current
        DESCRIPTION  
            "PMON data clear control response
            1:COMPLETED
            2:FAILED
            3:EXECUTING"
        ::= { ipeSysOpProgramPmonRmonClearEntry 4 }

    ipeFileSystemGroup OBJECT IDENTIFIER
        ::= { system5 2 }

    ipeFsFileInfoTable OBJECT-TYPE
        SYNTAX       SEQUENCE OF IpeFsFileInfoEntry
        MAX-ACCESS   not-accessible
        STATUS       current
        DESCRIPTION  "Table of file information."
        ::= { ipeFileSystemGroup 1 }

    ipeFsFileInfoEntry OBJECT-TYPE
        SYNTAX       IpeFsFileInfoEntry
        MAX-ACCESS   not-accessible
        STATUS       current
        DESCRIPTION  "Entry of file information."
        INDEX        { ipeFsFileInfoIndex }
        ::= { ipeFsFileInfoTable 1 }

    IpeFsFileInfoEntry ::= SEQUENCE {
        ipeFsFileInfoIndex            Integer32,
        ipeFsFileInfoNEAddress        IpAddress,
        ipeFsFileListType             INTEGER,
        ipeFsFileListCurrent          DisplayString,
        ipeFsFileListTemp             DisplayString,
        ipeFsUpdateFileDetail         DisplayString,
        ipeFsUpdateFileStatus         INTEGER,
        ipeFsUpdateFileStatusDetail   OCTET STRING,
        ipeFsUpdateFileProgressBase   Integer32,
        ipeFsUpdateFileProgress       Integer32,
        ipeFsUpdateFileUpdateList     DisplayString,
        ipeFsUpdateFileConfigPartial  OCTET STRING
    }

    ipeFsFileInfoIndex OBJECT-TYPE
        SYNTAX       Integer32 (1..1)
        MAX-ACCESS   not-accessible
        STATUS       current
        DESCRIPTION  "Index of this table."
        ::= { ipeFsFileInfoEntry 1 }

    ipeFsFileInfoNEAddress OBJECT-TYPE
        SYNTAX       IpAddress
        MAX-ACCESS   not-accessible
        STATUS       current
        DESCRIPTION  "reserved."
        ::= { ipeFsFileInfoEntry 2 }

    ipeFsFileListType OBJECT-TYPE
        SYNTAX       INTEGER {
                         invalid(0),
                         idu(1),
                         odu(2),
                         mdprm(3),
                         raFpga(4),
                         ipeFpga(5),
                         softkey(7),
                         cfgNet(8),
                         cfgEqu(9),
                         cfgUser(10),
                         https(11),
                         pmon(12),
                         rmon(13),
                         log(14),
                         inventory(15),
                         mac(16),
                         all(17)
                     }
        MAX-ACCESS   read-write
        STATUS       current
        DESCRIPTION  
            "Type for acquisition
            
            0:Invalidity
            1: IDU
            2: ODU
            3: MODEM Parameter
            4: FPGA(Other slot)
            5: FPGA(Ctrl)
            6: MSE
            7: Software Key License
            8: Network Config
            9: Equipment Config
            10: User Config
            11: Server Certificate for HTTPS/HTTPS certificate issue request
            12: PMON data
            13: RMON data
            14: Command/event/alarm LOG
            15: Device Inventory file
            16: MAC learning entry
            17: all(All types)
            18: Card Firmware
            19: Private key for SSL Server Certificate
            20: CSR (Certificate Signing Request) for SSL Server Certificate
            21: CA (Certification Authority) certificate for SSL Server
            Certificate
            22: Modem Controller(valid for MODEM-AV)
            
            *'0:Invalidity' is used as an initial state.
            
            *Pertinent details: ipeFsFileListCurrent
            *Pertinent details: ipeFsFileListTemp"
        ::= { ipeFsFileInfoEntry 3 }

    ipeFsFileListCurrent OBJECT-TYPE
        SYNTAX       DisplayString
        MAX-ACCESS   read-only
        STATUS       current
        DESCRIPTION  
            "Current file list (Flash-ROM).
            
            The list of the type set to ipeFsFileListType is acquired. 
            
            Form of file list:
            
            It's 1 item by  'file name (It included in a path),file
            size,CRC'.
            Each item is divided at space.
            
            *CRC is fixed '0'. 
            
            Ex) FilePath1/FileName1,size,CRC FilePath2/FileName2,size,CRC...
            
            [Indispensable condition]
            *ipeFsFileListType setup is indispensable."
        ::= { ipeFsFileInfoEntry 4 }

    ipeFsFileListTemp OBJECT-TYPE
        SYNTAX       DisplayString
        MAX-ACCESS   read-only
        STATUS       current
        DESCRIPTION  
            "Temporary file list (DRAM).
            
            The list of the type set to ipeFsFileListType is acquired. 
            
            Form of file list:
            
            It's 1 item by 'file name (It isn't included in a pass),file
            size,CRC'.
            Each item is divided at space.
            
            *CRC is fixed '0'. 
            
            Ex) Filename1,size,CRC Filename2,size,CRC...
            
            [Indispensable condition]
            *ipeFsFileListType setup is indispensable."
        ::= { ipeFsFileInfoEntry 5 }

    ipeFsUpdateFileDetail OBJECT-TYPE
        SYNTAX       DisplayString
        MAX-ACCESS   read-write
        STATUS       current
        DESCRIPTION  
            "File update control.
            
            Thing to specify object file after it downloads it by
            'ipeSysOpFileDownloadCtrl','ipeFsUsbCommand' and to demand file
            update.
            
            Ex) Filename1
            
            *The object file name allows only alphanumeric character '0-9',
            'a-z', 'A-Z' of ASCII code, and sign '-_.+'.
            
            *Pertinent details: ipeSysOpFileDownloadModule
            *Pertinent details: ipeFsUpdateFileUpdateList
            *Pertinent details: ipeSysOpFileDownloadStatus
            *Pertinent details: ipeFsUpdateFileStatus
            *Pertinent details: ipeFsUsbProcStatus
            
            [Race condition]
            *When ipeSysOpFileDownloadStatus is (3:Executing) or
            (4:Suspending), it is invalid.
            *When ipeFsUpdateFileStatusis(3:Executing), it is invalid. 
            *When ipeFsUsbProcStatus is (2:Normal :Process executing), it is
            invalid.
            
            [Indispensable condition]
            *When ipeSysOpFileDownloadModule is 'odu(2)', 'mdprm(3)', or
            'raFpga(4)', ipeFsUpdateFileUpdateList setup is indispensable."
        ::= { ipeFsFileInfoEntry 6 }

    ipeFsUpdateFileStatus OBJECT-TYPE
        SYNTAX       INTEGER {
                         invalid(0),
                         success(1),
                         failure(2),
                         executing(3),
                         checking(4),
                         successWithoutRestrictedUser(5)
                     }
        MAX-ACCESS   read-only
        STATUS       current
        DESCRIPTION  
            "Update result.
              0:Invalidity
              1:Success
              2:Failed
              3:Executing
              4:Checking
              5:Success but some restricted UserName(s) are ignored
            
            *'0:Invalidity' is used as an initial state.
            
            *The slot result of the correspondence is set to
            'IpeFsUpdateFileStatusDetail',
              and processing is continued when failing in the two or more
            slot update.
            
            *Pertinent details: ipeFsUpdateFileDetail
            *Pertinent details: ipeFsUpdateFileStatusDetail"
        ::= { ipeFsFileInfoEntry 7 }

    ipeFsUpdateFileStatusDetail OBJECT-TYPE
        SYNTAX       OCTET STRING (SIZE(42..42))
        MAX-ACCESS   read-only
        STATUS       current
        DESCRIPTION  
            "Update result is detailed. 
            
            OCT: Update result of each slot
                  1: Completed
                  2: Failed
            
            The slot for which the current state is used becomes the
            following.
            
            OCT[0] : MainBoard(iPASO200)   or SLOT0
            OCT[1] : MODEM1(iPASO200)      or SLOT1
            OCT[2] : MODEM2(iPASO200)      or SLOT2
            OCT[3] : Option Card(iPASO200) or SLOT3
              :
            OCT[33]: ODU1
            OCT[34]: ODU2
            OCT[35]: ODU3
              :
            
            *Pertinent details: ipeSysOpFileDownloadCtrl
            *Pertinent details: ipeFsUpdateFileDetail
            *Pertinent details: ipeFsUsbCommand"
        ::= { ipeFsFileInfoEntry 8 }

    ipeFsUpdateFileProgressBase OBJECT-TYPE
        SYNTAX       Integer32
        MAX-ACCESS   read-only
        STATUS       current
        DESCRIPTION  
            "Progress of update (denominator).
            
            *Pertinent details: ipeSysOpFileDownloadModule
            *Pertinent details: ipeFsUpdateFileStatus"
        ::= { ipeFsFileInfoEntry 9 }

    ipeFsUpdateFileProgress OBJECT-TYPE
        SYNTAX       Integer32
        MAX-ACCESS   read-only
        STATUS       current
        DESCRIPTION  
            "Progress of update (molecule).
            
            *Pertinent details: ipeSysOpFileDownloadModule
            *Pertinent details: ipeFsUpdateFileStatus"
        ::= { ipeFsFileInfoEntry 10 }

    ipeFsUpdateFileUpdateList OBJECT-TYPE
        SYNTAX       DisplayString
        MAX-ACCESS   read-write
        STATUS       current
        DESCRIPTION  
            "Definition of update slot number.
            
            Form of file list:
            When downloading it to ODU/FPGA/MDPRM, the forwarding site slot
            number is enumerated by a comma end.
            
            Ex) 0,5,1,6,10...
              The slot number of relating MODEM and fpga must set the slot
            number of
              Option Card to odu and mdprm according to inventory
            information.
            
            The slot number to which the current state can be set becomes the
            following.
            
            iPASO200             iPASO400,1000
            0 : MainBoard     or SLOT0
            1 : MODEM1        or SLOT1
            2 : MODEM2        or SLOT2
            3 : Option Card   or SLOT3
                  :
            33: ODU1
            34: ODU2
            35: ODU3
                  :
            
            *Pertinent details: ipeFsUpdateFileDetail"
        ::= { ipeFsFileInfoEntry 11 }

    ipeFsUpdateFileConfigPartial OBJECT-TYPE
        SYNTAX       OCTET STRING (SIZE(4..4))
        MAX-ACCESS   read-write
        STATUS       current
        DESCRIPTION  
            "Specify Equipment Configuration Partial Download pattern.
            If this object is set with ipeFsUpdateFileDetail, the system will
            perform the partial download, otherwise the system will perform
            the normal download. And Partial Download is performed only when
            Equipment Configuration Dowload.
            
            SYNTAX is 32bit string. The definition of each bit is shown
            below.
            
            - bit1-4: specify download mode.
             0001 : normal mode
             other value : reserved (system rejects the request)
            - bit5-32: specify the equipment config part. Setting 1 to each
            bit means corresponding config download is activated.
             Bit5 : Equipment Configuration (must set when the normal mode)
             Bit6 : Radio Configuration
             Bit7 : Radio Configuration w/o Radio Frequency
                    Bit6 and Bit7 cannot be set to 1 simultaneously.
             Bit8 : E1/STM1 Mapping (must set when Bit6 or Bit7 is activated)
             Bit9 : MODEM Function setting
             Bit10: ETH Function setting
             Bit11: E1/STM1/Cross Connect Setting
             Bit12: PWE Setting
             Bit13: Equipment Clock/Synchronization Setting
             Bit14: Relay-Alarm Mapping
             Bit15: V11/OW Setting
             Bit16: Alarm/AIS Setting
             Bit17: PMON/RMON Setting
             Bit18: AUX Setting
            
             other: reserved (don't care)
            
            Example)
             the pattern of downloading the equipment configuration, radio
            configuration, E1/STM1 mapping, ETH Function Setting on normal
            mode.
              ipeFsUpdateFileConfigPartial = 
                      '00011101010000000000000000000000'"
        ::= { ipeFsFileInfoEntry 12 }

    ipeFsUsbInfoTable OBJECT-TYPE
        SYNTAX       SEQUENCE OF IpeFsUsbInfoEntry
        MAX-ACCESS   not-accessible
        STATUS       current
        DESCRIPTION  "Table of USB memory information."
        ::= { ipeFileSystemGroup 2 }

    ipeFsUsbInfoEntry OBJECT-TYPE
        SYNTAX       IpeFsUsbInfoEntry
        MAX-ACCESS   not-accessible
        STATUS       current
        DESCRIPTION  "Entry of USB mamory information."
        INDEX        { ipeFsUsbInfoIndex }
        ::= { ipeFsUsbInfoTable 1 }

    IpeFsUsbInfoEntry ::= SEQUENCE {
        ipeFsUsbInfoIndex      Integer32,
        ipeFsUsbInfoNEAddress  IpAddress,
        ipeFsUsbCommand        DisplayString,
        ipeFsUsbProcStatus     INTEGER,
        ipeFsUsbList           DisplayString,
        ipeFsUsbConnectStatus  INTEGER
    }

    ipeFsUsbInfoIndex OBJECT-TYPE
        SYNTAX       Integer32 (1..1)
        MAX-ACCESS   not-accessible
        STATUS       current
        DESCRIPTION  "Index of this table."
        ::= { ipeFsUsbInfoEntry 1 }

    ipeFsUsbInfoNEAddress OBJECT-TYPE
        SYNTAX       IpAddress
        MAX-ACCESS   not-accessible
        STATUS       current
        DESCRIPTION  "reserved."
        ::= { ipeFsUsbInfoEntry 2 }

    ipeFsUsbCommand OBJECT-TYPE
        SYNTAX       DisplayString
        MAX-ACCESS   read-write
        STATUS       current
        DESCRIPTION  
            "USB control mode/USB file path/Program type specification.
            
            [Mode],[Arg1],[Type]
              Mode:USB control mode
                0:DL, 1:UL
              Arg1:object file path -1 (original file path (path from a
            chroot subordinate) When DL: Inside of USB, When UL: Inside of
            IPE)
                  Case of DL: Ex.) idu/iPASOLINK200-idufw-v1.00.XX.bin
                  Case of UL: Ex.) export/config/iPASOLINK-network.cfg
              Type:Program type
                  The program type set to  'ipeSysOpFileDownloadModule' is
            specified.
                  *The unsetting is allowed for an arbitrary, set item. 
            
                 0: Invalid
                 1: IDU F/W
                 2: ODU F/W
                 3: MODEM Parameter
                 4: FPGA(Option Card)
                 5: FPGA(MainBoard)
                 6: MSE Card F/W
                 7: Software License Key
                 8: Network Config
                 9: Equipment Config
                10: User Config
                11: HTTPS Server Certificate
            
            *The object file name allows only alphanumeric character '0-9',
            'a-z', 'A-Z' of ASCII code, and sign '-_.+'.
            
            *Pertinent details: ipeSysOpFileDownloadModule
            *Pertinent details: ipeSysOpFileDownloadStatus
            *Pertinent details: ipeFsUpdateFileStatus
            *Pertinent details: ipeFsUsbProcStatus
            
            [Race condition]
            *When ipeSysOpFileDownloadStatus is (3:Executing) or
            (4:Suspending), (0:DL) is invalid.
            *When ipeFsUpdateFileStatusis (3:Executing),  (0:DL) is invalid.
            *When ipeFsUsbProcStatus is (2:Normal :Process executing), 
            (0:DL) is invalid."
        ::= { ipeFsUsbInfoEntry 3 }

    ipeFsUsbProcStatus OBJECT-TYPE
        SYNTAX       INTEGER {
                         invalid(0),
                         completed(1),
                         executing(2),
                         diskFullError(98),
                         noSuchFileError(99),
                         unKnownFileError(101),
                         notInsertError(102),
                         accessError(103),
                         otherError(127)
                     }
        MAX-ACCESS   read-only
        STATUS       current
        DESCRIPTION  
            "Status of USB memory control result.
            
            The classification of a setting value and the meaning are as
            follows.
              0:Invalidity
              1:NORMAL:Normal end
              2:NORMAL:Executing
             98:ERROR:The lack of free space on disk or media
             99:ERROR:File/directory not found
            101:ERROR:The kind of designated files,the size, contents, etc.
            are unjust
            102:ERROR:Media aren't inserted
            103:ERROR:Media access error (ex:unjust format)
            127:ERROR:Undefined error (other errors)
            When having a control instruction, it's made '2:Executing'.
            
            *'0:Invalidity' is used as an initial state.
            
            *Pertinent details: ipeFsUsbCommand"
        ::= { ipeFsUsbInfoEntry 4 }

    ipeFsUsbList OBJECT-TYPE
        SYNTAX       DisplayString
        MAX-ACCESS   read-only
        STATUS       current
        DESCRIPTION  
            "File list format.
            
            Form of file list:
            
            It's 1 item by 'file name (path from a chroot subordinate),file
            size,CRC'.
            Each item is divided at space.
            
            *CRC is fixed '0'. 
            
            Ex) FilePath1/FileName1,size,CRC FilePath2/FileName2,size,CRC..."
        ::= { ipeFsUsbInfoEntry 5 }

    ipeFsUsbConnectStatus OBJECT-TYPE
        SYNTAX       INTEGER { usbConnect(1), usbNoConnect(2) }
        MAX-ACCESS   read-only
        STATUS       current
        DESCRIPTION  
            "Status of connection USB memory.
            
            1:Connect
            2:Not connect"
        ::= { ipeFsUsbInfoEntry 6 }

    ipeConfigurationGroup OBJECT IDENTIFIER
        ::= { system5 3 }

    ipeCfgSystemTable OBJECT-TYPE
        SYNTAX       SEQUENCE OF IpeCfgSystemEntry
        MAX-ACCESS   not-accessible
        STATUS       current
        DESCRIPTION  "Table of System Item Information."
        ::= { ipeConfigurationGroup 1 }

    ipeCfgSystemEntry OBJECT-TYPE
        SYNTAX       IpeCfgSystemEntry
        MAX-ACCESS   not-accessible
        STATUS       current
        DESCRIPTION  "Entry of System Item Information."
        INDEX        { ipeCfgSystemIndex }
        ::= { ipeCfgSystemTable 1 }

    IpeCfgSystemEntry ::= SEQUENCE {
        ipeCfgSystemIndex      Integer32,
        ipeCfgSystemNEAddress  IpAddress,
        ipeCfgNeName           DisplayString,
        ipeCfgAreaName         DisplayString,
        ipeCfgMemo             DisplayString
    }

    ipeCfgSystemIndex OBJECT-TYPE
        SYNTAX       Integer32 (1..1)
        MAX-ACCESS   not-accessible
        STATUS       current
        DESCRIPTION  "Index of this table."
        ::= { ipeCfgSystemEntry 1 }

    ipeCfgSystemNEAddress OBJECT-TYPE
        SYNTAX       IpAddress
        MAX-ACCESS   not-accessible
        STATUS       current
        DESCRIPTION  "reserved."
        ::= { ipeCfgSystemEntry 2 }

    ipeCfgNeName OBJECT-TYPE
        SYNTAX       DisplayString
        MAX-ACCESS   read-write
        STATUS       current
        DESCRIPTION  
            "PASOLINK unit name. White space characters are not allowed for
            head or tail of characters."
        ::= { ipeCfgSystemEntry 3 }

    ipeCfgAreaName OBJECT-TYPE
        SYNTAX       DisplayString
        MAX-ACCESS   read-write
        STATUS       current
        DESCRIPTION  
            "Area name. White space characters are not allowed for head or
            tail of characters."
        ::= { ipeCfgSystemEntry 4 }

    ipeCfgMemo OBJECT-TYPE
        SYNTAX       DisplayString
        MAX-ACCESS   read-write
        STATUS       current
        DESCRIPTION  
            "Memorandum. White space characters are not allowed for head or
            tail of characters."
        ::= { ipeCfgSystemEntry 5 }

    ipeCfgOemTable OBJECT-TYPE
        SYNTAX       SEQUENCE OF IpeCfgOemEntry
        MAX-ACCESS   not-accessible
        STATUS       current
        DESCRIPTION  "Table of Equipment Item Information."
        ::= { ipeConfigurationGroup 2 }

    ipeCfgOemEntry OBJECT-TYPE
        SYNTAX       IpeCfgOemEntry
        MAX-ACCESS   not-accessible
        STATUS       current
        DESCRIPTION  "Entry of Equipment Item Information."
        INDEX        { ipeCfgOemIndex }
        ::= { ipeCfgOemTable 1 }

    IpeCfgOemEntry ::= SEQUENCE {
        ipeCfgOemIndex        Integer32,
        ipeCfgOemNEAddress    IpAddress,
        ipeCfgOemSysDescr     DisplayString,
        ipeCfgOemSysContact   DisplayString,
        ipeCfgOemSysName      DisplayString,
        ipeCfgOemSysLocation  DisplayString
    }

    ipeCfgOemIndex OBJECT-TYPE
        SYNTAX       Integer32 (1..1)
        MAX-ACCESS   not-accessible
        STATUS       current
        DESCRIPTION  "Index of this table."
        ::= { ipeCfgOemEntry 1 }

    ipeCfgOemNEAddress OBJECT-TYPE
        SYNTAX       IpAddress
        MAX-ACCESS   not-accessible
        STATUS       current
        DESCRIPTION  "reserved."
        ::= { ipeCfgOemEntry 2 }

    ipeCfgOemSysDescr OBJECT-TYPE
        SYNTAX       DisplayString
        MAX-ACCESS   read-write
        STATUS       current
        DESCRIPTION  
            "System Description.
            The space of the begininng and end dose not permit it."
        ::= { ipeCfgOemEntry 3 }

    ipeCfgOemSysContact OBJECT-TYPE
        SYNTAX       DisplayString
        MAX-ACCESS   read-write
        STATUS       current
        DESCRIPTION  
            "System contact.
            The space of the begininng and end dose not permit it."
        ::= { ipeCfgOemEntry 4 }

    ipeCfgOemSysName OBJECT-TYPE
        SYNTAX       DisplayString
        MAX-ACCESS   read-write
        STATUS       current
        DESCRIPTION  
            "System name.
            The space of the begininng and end dose not permit it."
        ::= { ipeCfgOemEntry 5 }

    ipeCfgOemSysLocation OBJECT-TYPE
        SYNTAX       DisplayString
        MAX-ACCESS   read-write
        STATUS       current
        DESCRIPTION  
            "System location.
            The space of the begininng and end dose not permit it."
        ::= { ipeCfgOemEntry 6 }

    ipeCfgAux OBJECT IDENTIFIER
        ::= { ipeConfigurationGroup 3 }

    ipeCfgAuxInTable OBJECT-TYPE
        SYNTAX       SEQUENCE OF IpeCfgAuxInEntry
        MAX-ACCESS   not-accessible
        STATUS       current
        DESCRIPTION  "Aux Input Table"
        ::= { ipeCfgAux 1 }

    ipeCfgAuxInEntry OBJECT-TYPE
        SYNTAX       IpeCfgAuxInEntry
        MAX-ACCESS   not-accessible
        STATUS       current
        DESCRIPTION  ""
        INDEX        { ipeCfgAuxInIndex }
        ::= { ipeCfgAuxInTable 1 }

    IpeCfgAuxInEntry ::= SEQUENCE {
        ipeCfgAuxInIndex          Integer32,
        ipeCfgAuxInNEAddress      IpAddress,
        ipeCfgAuxInItemName       DisplayString,
        ipeCfgAuxInItemType       INTEGER,
        ipeCfgAuxInOpenState      DisplayString,
        ipeCfgAuxInCloseState     DisplayString,
        ipeCfgAuxInSeverity       INTEGER,
        ipeCfgAuxInAlarmType      AlarmTypeValue,
        ipeCfgAuxInProbableCause  ProbableCauseValue
    }

    ipeCfgAuxInIndex OBJECT-TYPE
        SYNTAX       Integer32
        MAX-ACCESS   not-accessible
        STATUS       current
        DESCRIPTION  "Index of this table."
        ::= { ipeCfgAuxInEntry 1 }

    ipeCfgAuxInNEAddress OBJECT-TYPE
        SYNTAX       IpAddress
        MAX-ACCESS   not-accessible
        STATUS       current
        DESCRIPTION  "reserved."
        ::= { ipeCfgAuxInEntry 2 }

    ipeCfgAuxInItemName OBJECT-TYPE
        SYNTAX       DisplayString (SIZE(0..32))
        MAX-ACCESS   read-write
        STATUS       current
        DESCRIPTION  "Item Name"
        ::= { ipeCfgAuxInEntry 3 }

    ipeCfgAuxInItemType OBJECT-TYPE
        SYNTAX       INTEGER { alarmInOpen(1), alarmInClose(2), status(3) }
        MAX-ACCESS   read-write
        STATUS       current
        DESCRIPTION  "Item Type"
        ::= { ipeCfgAuxInEntry 4 }

    ipeCfgAuxInOpenState OBJECT-TYPE
        SYNTAX       DisplayString (SIZE(0..32))
        MAX-ACCESS   read-write
        STATUS       current
        DESCRIPTION  "Status Strings (Event Off (Open))"
        ::= { ipeCfgAuxInEntry 5 }

    ipeCfgAuxInCloseState OBJECT-TYPE
        SYNTAX       DisplayString (SIZE(0..32))
        MAX-ACCESS   read-write
        STATUS       current
        DESCRIPTION  "Status Strings (Event On (Close))"
        ::= { ipeCfgAuxInEntry 6 }

    ipeCfgAuxInSeverity OBJECT-TYPE
        SYNTAX       INTEGER {
                         invalid(0),
                         critical(1),
                         major(2),
                         minor(3),
                         warning(4)
                     }
        MAX-ACCESS   read-write
        STATUS       current
        DESCRIPTION  "Severity (X.733)"
        ::= { ipeCfgAuxInEntry 7 }

    ipeCfgAuxInAlarmType OBJECT-TYPE
        SYNTAX       AlarmTypeValue
        MAX-ACCESS   read-write
        STATUS       current
        DESCRIPTION  "Alarm Type (X.733)"
        ::= { ipeCfgAuxInEntry 8 }

    ipeCfgAuxInProbableCause OBJECT-TYPE
        SYNTAX       ProbableCauseValue
        MAX-ACCESS   read-write
        STATUS       current
        DESCRIPTION  "Probable Cause (X.733)"
        ::= { ipeCfgAuxInEntry 9 }

    ipeCfgAuxOutTable OBJECT-TYPE
        SYNTAX       SEQUENCE OF IpeCfgAuxOutEntry
        MAX-ACCESS   not-accessible
        STATUS       current
        DESCRIPTION  "AUX Output Table"
        ::= { ipeCfgAux 2 }

    ipeCfgAuxOutEntry OBJECT-TYPE
        SYNTAX       IpeCfgAuxOutEntry
        MAX-ACCESS   not-accessible
        STATUS       current
        DESCRIPTION  ""
        INDEX        { ipeCfgAuxOutIndex }
        ::= { ipeCfgAuxOutTable 1 }

    IpeCfgAuxOutEntry ::= SEQUENCE {
        ipeCfgAuxOutIndex       Integer32,
        ipeCfgAuxOutNEAddress   IpAddress,
        ipeCfgAuxOutItemName    DisplayString,
        ipeCfgAuxOutOpenState   DisplayString,
        ipeCfgAuxOutCloseState  DisplayString
    }

    ipeCfgAuxOutIndex OBJECT-TYPE
        SYNTAX       Integer32
        MAX-ACCESS   not-accessible
        STATUS       current
        DESCRIPTION  "Index of this table."
        ::= { ipeCfgAuxOutEntry 1 }

    ipeCfgAuxOutNEAddress OBJECT-TYPE
        SYNTAX       IpAddress
        MAX-ACCESS   not-accessible
        STATUS       current
        DESCRIPTION  "reserved."
        ::= { ipeCfgAuxOutEntry 2 }

    ipeCfgAuxOutItemName OBJECT-TYPE
        SYNTAX       DisplayString (SIZE(0..32))
        MAX-ACCESS   read-write
        STATUS       current
        DESCRIPTION  "Item Name"
        ::= { ipeCfgAuxOutEntry 3 }

    ipeCfgAuxOutOpenState OBJECT-TYPE
        SYNTAX       DisplayString (SIZE(0..32))
        MAX-ACCESS   read-write
        STATUS       current
        DESCRIPTION  "Status Strings (Event Off (Open))"
        ::= { ipeCfgAuxOutEntry 4 }

    ipeCfgAuxOutCloseState OBJECT-TYPE
        SYNTAX       DisplayString (SIZE(0..32))
        MAX-ACCESS   read-write
        STATUS       current
        DESCRIPTION  "Status Strings (Event On (Close))"
        ::= { ipeCfgAuxOutEntry 5 }

    ipeCfgNtp OBJECT IDENTIFIER
        ::= { ipeConfigurationGroup 4 }

    ipeCfgNtpServiceTable OBJECT-TYPE
        SYNTAX       SEQUENCE OF IpeCfgNtpServiceEntry
        MAX-ACCESS   not-accessible
        STATUS       current
        DESCRIPTION  "Table of NTP configuration information."
        ::= { ipeCfgNtp 1 }

    ipeCfgNtpServiceEntry OBJECT-TYPE
        SYNTAX       IpeCfgNtpServiceEntry
        MAX-ACCESS   not-accessible
        STATUS       current
        DESCRIPTION  "Entry of NTP configuration information."
        INDEX        { ipeCfgNtpServiceIndex }
        ::= { ipeCfgNtpServiceTable 1 }

    IpeCfgNtpServiceEntry ::= SEQUENCE {
        ipeCfgNtpServiceIndex                 Integer32,
        ipeCfgNtpServiceNEAddress             IpAddress,
        ipeCfgNtpServiceEnable                INTEGER,
        ipeCfgNtpServerMode                   INTEGER,
        ipeCfgNtpClientMode                   INTEGER,
        ipeCfgNtpServerStratum                Integer32,
        ipeCfgNtpServerMulticastPort          Integer32,
        ipeCfgNtpServerMulticastIntervalTime  Integer32
    }

    ipeCfgNtpServiceIndex OBJECT-TYPE
        SYNTAX       Integer32 (1..1)
        MAX-ACCESS   not-accessible
        STATUS       current
        DESCRIPTION  "Index of this table."
        ::= { ipeCfgNtpServiceEntry 1 }

    ipeCfgNtpServiceNEAddress OBJECT-TYPE
        SYNTAX       IpAddress
        MAX-ACCESS   not-accessible
        STATUS       current
        DESCRIPTION  "reserved."
        ::= { ipeCfgNtpServiceEntry 2 }

    ipeCfgNtpServiceEnable OBJECT-TYPE
        SYNTAX       INTEGER { invalid(0), disabled(1), enabled(2) }
        MAX-ACCESS   read-write
        STATUS       current
        DESCRIPTION  "NTP control enable."
        ::= { ipeCfgNtpServiceEntry 3 }

    ipeCfgNtpServerMode OBJECT-TYPE
        SYNTAX       INTEGER { invalid(0), unicast(1), multicast(2), disabled(3) }
        MAX-ACCESS   read-write
        STATUS       current
        DESCRIPTION  "NTP server mode."
        ::= { ipeCfgNtpServiceEntry 4 }

    ipeCfgNtpClientMode OBJECT-TYPE
        SYNTAX       INTEGER { invalid(0), unicast(1), multicast(2), disabled(3) }
        MAX-ACCESS   read-write
        STATUS       current
        DESCRIPTION  "NTP client mode."
        ::= { ipeCfgNtpServiceEntry 5 }

    ipeCfgNtpServerStratum OBJECT-TYPE
        SYNTAX       Integer32 (2..15)
        MAX-ACCESS   read-write
        STATUS       current
        DESCRIPTION  "NTP Stratum."
        ::= { ipeCfgNtpServiceEntry 6 }

    ipeCfgNtpServerMulticastPort OBJECT-TYPE
        SYNTAX       Integer32
        MAX-ACCESS   read-write
        STATUS       current
        DESCRIPTION  "NTP server multicast port."
        ::= { ipeCfgNtpServiceEntry 7 }

    ipeCfgNtpServerMulticastIntervalTime OBJECT-TYPE
        SYNTAX       Integer32 (4..17)
        MAX-ACCESS   read-write
        STATUS       current
        DESCRIPTION  "Value of NTP multicast polling time."
        ::= { ipeCfgNtpServiceEntry 8 }

    ipeCfgNtpServerTable OBJECT-TYPE
        SYNTAX       SEQUENCE OF IpeCfgNtpServerEntry
        MAX-ACCESS   not-accessible
        STATUS       current
        DESCRIPTION  "Table of NTP server information."
        ::= { ipeCfgNtp 2 }

    ipeCfgNtpServerEntry OBJECT-TYPE
        SYNTAX       IpeCfgNtpServerEntry
        MAX-ACCESS   not-accessible
        STATUS       current
        DESCRIPTION  "Entry of NTP server information."
        INDEX        { ipeCfgNtpServerIndex }
        ::= { ipeCfgNtpServerTable 1 }

    IpeCfgNtpServerEntry ::= SEQUENCE {
        ipeCfgNtpServerIndex      Integer32,
        ipeCfgNtpServerNEAddress  IpAddress,
        ipeCfgNtpServerAddress    IpAddress,
        ipeCfgNtpVersion          Integer32,
        ipeCfgNtpPollTime         Integer32
    }

    ipeCfgNtpServerIndex OBJECT-TYPE
        SYNTAX       Integer32 (1..4)
        MAX-ACCESS   not-accessible
        STATUS       current
        DESCRIPTION  "Index of this table."
        ::= { ipeCfgNtpServerEntry 1 }

    ipeCfgNtpServerNEAddress OBJECT-TYPE
        SYNTAX       IpAddress
        MAX-ACCESS   not-accessible
        STATUS       current
        DESCRIPTION  "reserved."
        ::= { ipeCfgNtpServerEntry 2 }

    ipeCfgNtpServerAddress OBJECT-TYPE
        SYNTAX       IpAddress
        MAX-ACCESS   read-write
        STATUS       current
        DESCRIPTION  "IP Address of NTP server."
        ::= { ipeCfgNtpServerEntry 3 }

    ipeCfgNtpVersion OBJECT-TYPE
        SYNTAX       Integer32 (3..4)
        MAX-ACCESS   read-write
        STATUS       current
        DESCRIPTION  "Version of supported NTP message."
        ::= { ipeCfgNtpServerEntry 4 }

    ipeCfgNtpPollTime OBJECT-TYPE
        SYNTAX       Integer32 (4..17)
        MAX-ACCESS   read-write
        STATUS       current
        DESCRIPTION  
            "NTP Polling Time, in seconds as a power of two.
            For instance, a value of six indicates a interval of 64 seconds.
            
            Note) The value less than 6 is rejected by the agent because of
            the system recommendation.
             iPASOLINK 200/400/1000 series : R3.5 or later.
             iPASOLINK AOR : R1.0 or later."
        ::= { ipeCfgNtpServerEntry 5 }

    ipeCfgFtp OBJECT IDENTIFIER
        ::= { ipeConfigurationGroup 7 }

    ipeCfgFtpServerTable OBJECT-TYPE
        SYNTAX       SEQUENCE OF IpeCfgFtpServerEntry
        MAX-ACCESS   not-accessible
        STATUS       current
        DESCRIPTION  "Table of FTP server configuration information."
        ::= { ipeCfgFtp 1 }

    ipeCfgFtpServerEntry OBJECT-TYPE
        SYNTAX       IpeCfgFtpServerEntry
        MAX-ACCESS   not-accessible
        STATUS       current
        DESCRIPTION  "Entry of FTP server configuration information."
        INDEX        { ipeCfgFtpServerIndex }
        ::= { ipeCfgFtpServerTable 1 }

    IpeCfgFtpServerEntry ::= SEQUENCE {
        ipeCfgFtpServerIndex           Integer32,
        ipeCfgFtpServerNEAddress       IpAddress,
        ipeCfgFtpServerEnable          INTEGER,
        ipeCfgFtpServerCommandTcpPort  Integer32,
        ipeCfgFtpServerDataTcpPort     Integer32,
        ipeCfgFtpServerMaxSession      Integer32,
        ipeCfgFtpServerAutoDisable     INTEGER
    }

    ipeCfgFtpServerIndex OBJECT-TYPE
        SYNTAX       Integer32 (1..1)
        MAX-ACCESS   not-accessible
        STATUS       current
        DESCRIPTION  "Index of this table."
        ::= { ipeCfgFtpServerEntry 1 }

    ipeCfgFtpServerNEAddress OBJECT-TYPE
        SYNTAX       IpAddress
        MAX-ACCESS   not-accessible
        STATUS       current
        DESCRIPTION  "reserved."
        ::= { ipeCfgFtpServerEntry 2 }

    ipeCfgFtpServerEnable OBJECT-TYPE
        SYNTAX       INTEGER {
                         invalid(0),
                         serviceDisable(1),
                         serviceEnable(2),
                         alwaysEnable(3)
                     }
        MAX-ACCESS   read-write
        STATUS       current
        DESCRIPTION  "FTP control enable."
        ::= { ipeCfgFtpServerEntry 3 }

    ipeCfgFtpServerCommandTcpPort OBJECT-TYPE
        SYNTAX       Integer32 (1..65535)
        MAX-ACCESS   read-write
        STATUS       current
        DESCRIPTION  "Port number of FTP command."
        ::= { ipeCfgFtpServerEntry 4 }

    ipeCfgFtpServerDataTcpPort OBJECT-TYPE
        SYNTAX       Integer32 (1..65535)
        MAX-ACCESS   read-write
        STATUS       current
        DESCRIPTION  "Port number of FTP data transfer."
        ::= { ipeCfgFtpServerEntry 5 }

    ipeCfgFtpServerMaxSession OBJECT-TYPE
        SYNTAX       Integer32 (1..3)
        MAX-ACCESS   read-write
        STATUS       current
        DESCRIPTION  "Number of max connections."
        ::= { ipeCfgFtpServerEntry 6 }

    ipeCfgFtpServerAutoDisable OBJECT-TYPE
        SYNTAX       INTEGER { invalid(0), disabled(1), enabled(2) }
        MAX-ACCESS   read-write
        STATUS       current
        DESCRIPTION  "FTP automatic stop control enable."
        ::= { ipeCfgFtpServerEntry 7 }

    ipeCfgSftp OBJECT IDENTIFIER
        ::= { ipeConfigurationGroup 8 }

    ipeCfgSftpServerTable OBJECT-TYPE
        SYNTAX       SEQUENCE OF IpeCfgSftpServerEntry
        MAX-ACCESS   not-accessible
        STATUS       current
        DESCRIPTION  "Table of SFTP server configuration information."
        ::= { ipeCfgSftp 1 }

    ipeCfgSftpServerEntry OBJECT-TYPE
        SYNTAX       IpeCfgSftpServerEntry
        MAX-ACCESS   not-accessible
        STATUS       current
        DESCRIPTION  "Entry of SFTP server configuration information."
        INDEX        { ipeCfgSftpServerIndex }
        ::= { ipeCfgSftpServerTable 1 }

    IpeCfgSftpServerEntry ::= SEQUENCE {
        ipeCfgSftpServerIndex        Integer32,
        ipeCfgSftpServerNEAddress    IpAddress,
        ipeCfgSftpServerEnable       INTEGER,
        ipeCfgSftpServerAutoDisable  INTEGER
    }

    ipeCfgSftpServerIndex OBJECT-TYPE
        SYNTAX       Integer32 (1..1)
        MAX-ACCESS   not-accessible
        STATUS       current
        DESCRIPTION  "Index of this table."
        ::= { ipeCfgSftpServerEntry 1 }

    ipeCfgSftpServerNEAddress OBJECT-TYPE
        SYNTAX       IpAddress
        MAX-ACCESS   not-accessible
        STATUS       current
        DESCRIPTION  "reserved."
        ::= { ipeCfgSftpServerEntry 2 }

    ipeCfgSftpServerEnable OBJECT-TYPE
        SYNTAX       INTEGER {
                         invalid(0),
                         serviceDisable(1),
                         serviceEnable(2),
                         alwaysEnable(3)
                     }
        MAX-ACCESS   read-write
        STATUS       current
        DESCRIPTION  "SFTP control enable."
        ::= { ipeCfgSftpServerEntry 3 }

    ipeCfgSftpServerAutoDisable OBJECT-TYPE
        SYNTAX       INTEGER { invalid(0), disabled(1), enabled(2) }
        MAX-ACCESS   read-write
        STATUS       current
        DESCRIPTION  "SFTP automatic stop control enable."
        ::= { ipeCfgSftpServerEntry 4 }

    ipeCfgHttp OBJECT IDENTIFIER
        ::= { ipeConfigurationGroup 9 }

    ipeCfgHttpServerTable OBJECT-TYPE
        SYNTAX       SEQUENCE OF IpeCfgHttpServerEntry
        MAX-ACCESS   not-accessible
        STATUS       current
        DESCRIPTION  "Table of HTTP configuration information."
        ::= { ipeCfgHttp 1 }

    ipeCfgHttpServerEntry OBJECT-TYPE
        SYNTAX       IpeCfgHttpServerEntry
        MAX-ACCESS   not-accessible
        STATUS       current
        DESCRIPTION  "Entry of HTTP configuration information."
        INDEX        { ipeCfgHttpServerIndex }
        ::= { ipeCfgHttpServerTable 1 }

    IpeCfgHttpServerEntry ::= SEQUENCE {
        ipeCfgHttpServerIndex      Integer32,
        ipeCfgHttpServerNEAddress  IpAddress,
        ipeCfgHttpServerEnable     INTEGER,
        ipeCfgHttpServerTcpPort    Integer32
    }

    ipeCfgHttpServerIndex OBJECT-TYPE
        SYNTAX       Integer32 (1..1)
        MAX-ACCESS   not-accessible
        STATUS       current
        DESCRIPTION  "Index of this table."
        ::= { ipeCfgHttpServerEntry 1 }

    ipeCfgHttpServerNEAddress OBJECT-TYPE
        SYNTAX       IpAddress
        MAX-ACCESS   not-accessible
        STATUS       current
        DESCRIPTION  "reserved."
        ::= { ipeCfgHttpServerEntry 2 }

    ipeCfgHttpServerEnable OBJECT-TYPE
        SYNTAX       INTEGER { invalid(0), disabled(1), enabled(2) }
        MAX-ACCESS   read-write
        STATUS       current
        DESCRIPTION  "HTTP control enable."
        ::= { ipeCfgHttpServerEntry 3 }

    ipeCfgHttpServerTcpPort OBJECT-TYPE
        SYNTAX       Integer32 (1..65535)
        MAX-ACCESS   read-write
        STATUS       current
        DESCRIPTION  "Port number of HTTP."
        ::= { ipeCfgHttpServerEntry 4 }

    ipeCfgHttps OBJECT IDENTIFIER
        ::= { ipeConfigurationGroup 10 }

    ipeCfgHttpsServerTable OBJECT-TYPE
        SYNTAX       SEQUENCE OF IpeCfgHttpsServerEntry
        MAX-ACCESS   not-accessible
        STATUS       current
        DESCRIPTION  "Table of HTTPS configuration information."
        ::= { ipeCfgHttps 1 }

    ipeCfgHttpsServerEntry OBJECT-TYPE
        SYNTAX       IpeCfgHttpsServerEntry
        MAX-ACCESS   not-accessible
        STATUS       current
        DESCRIPTION  "Entry of HTTPS configuration information."
        INDEX        { ipeCfgHttpsServerIndex }
        ::= { ipeCfgHttpsServerTable 1 }

    IpeCfgHttpsServerEntry ::= SEQUENCE {
        ipeCfgHttpsServerIndex      Integer32,
        ipeCfgHttpsServerNEAddress  IpAddress,
        ipeCfgHttpsServerEnable     INTEGER,
        ipeCfgHttpsServerTcpPort    Integer32
    }

    ipeCfgHttpsServerIndex OBJECT-TYPE
        SYNTAX       Integer32 (1..1)
        MAX-ACCESS   not-accessible
        STATUS       current
        DESCRIPTION  "Index of this table."
        ::= { ipeCfgHttpsServerEntry 1 }

    ipeCfgHttpsServerNEAddress OBJECT-TYPE
        SYNTAX       IpAddress
        MAX-ACCESS   not-accessible
        STATUS       current
        DESCRIPTION  "reserved."
        ::= { ipeCfgHttpsServerEntry 2 }

    ipeCfgHttpsServerEnable OBJECT-TYPE
        SYNTAX       INTEGER { invalid(0), disabled(1), enabled(2) }
        MAX-ACCESS   read-write
        STATUS       current
        DESCRIPTION  "HTTPS control enable."
        ::= { ipeCfgHttpsServerEntry 3 }

    ipeCfgHttpsServerTcpPort OBJECT-TYPE
        SYNTAX       Integer32 (1..65535)
        MAX-ACCESS   read-write
        STATUS       current
        DESCRIPTION  "TCP port number of HTTPS."
        ::= { ipeCfgHttpsServerEntry 4 }

    ipeCfgSnmp OBJECT IDENTIFIER
        ::= { ipeConfigurationGroup 11 }

    ipeCfgSnmpServerTable OBJECT-TYPE
        SYNTAX       SEQUENCE OF IpeCfgSnmpServerEntry
        MAX-ACCESS   not-accessible
        STATUS       current
        DESCRIPTION  "A table of SNMP configuration information."
        ::= { ipeCfgSnmp 1 }

    ipeCfgSnmpServerEntry OBJECT-TYPE
        SYNTAX       IpeCfgSnmpServerEntry
        MAX-ACCESS   not-accessible
        STATUS       current
        DESCRIPTION  "A set of SNMP configuration information."
        INDEX        { ipeCfgSnmpServerIndex }
        ::= { ipeCfgSnmpServerTable 1 }

    IpeCfgSnmpServerEntry ::= SEQUENCE {
        ipeCfgSnmpServerIndex      Integer32,
        ipeCfgSnmpServerNEAddress  IpAddress,
        ipeCfgSnmpV1V2cEnable      INTEGER,
        ipeCfgSnmpV3Enable         INTEGER,
        ipeCfgSnmpServerPort       Integer32
    }

    ipeCfgSnmpServerIndex OBJECT-TYPE
        SYNTAX       Integer32 (1..1)
        MAX-ACCESS   not-accessible
        STATUS       current
        DESCRIPTION  "Index of this table."
        ::= { ipeCfgSnmpServerEntry 1 }

    ipeCfgSnmpServerNEAddress OBJECT-TYPE
        SYNTAX       IpAddress
        MAX-ACCESS   not-accessible
        STATUS       current
        DESCRIPTION  "reserved."
        ::= { ipeCfgSnmpServerEntry 2 }

    ipeCfgSnmpV1V2cEnable OBJECT-TYPE
        SYNTAX       INTEGER { invalid(0), disabled(1), enabled(2) }
        MAX-ACCESS   read-write
        STATUS       current
        DESCRIPTION  
            "Indicates the SNMP entity is permitted to receive & process
            SNMPv1/v2c PDU or is not permitted to do.
            
            Even if it is disabled, SNMPv1/v2c Traps is sent."
        ::= { ipeCfgSnmpServerEntry 3 }

    ipeCfgSnmpV3Enable OBJECT-TYPE
        SYNTAX       INTEGER { invalid(0), disabled(1), enabled(2) }
        MAX-ACCESS   read-write
        STATUS       current
        DESCRIPTION  
            "Indicates the SNMP entity is permitted to receive & process
            SNMPv3 PDU or is not permitted to do.
            
            Even if it is disabled, SNMPv3 Traps is sent."
        ::= { ipeCfgSnmpServerEntry 4 }

    ipeCfgSnmpServerPort OBJECT-TYPE
        SYNTAX       Integer32 (1..65535)
        MAX-ACCESS   read-write
        STATUS       current
        DESCRIPTION  
            "A UDP port number to receive all SNMP Request-PDU.
            The reboot of the system is necessary to reflect setting."
        ::= { ipeCfgSnmpServerEntry 5 }

    ipeCfgSnmpCommunityTable OBJECT-TYPE
        SYNTAX       SEQUENCE OF IpeCfgSnmpCommunityEntry
        MAX-ACCESS   not-accessible
        STATUS       current
        DESCRIPTION  "A table of SNMP community information."
        ::= { ipeCfgSnmp 2 }

    ipeCfgSnmpCommunityEntry OBJECT-TYPE
        SYNTAX       IpeCfgSnmpCommunityEntry
        MAX-ACCESS   not-accessible
        STATUS       current
        DESCRIPTION  "A set of SNMP community information."
        INDEX        { ipeCfgSnmpCommunityIndex }
        ::= { ipeCfgSnmpCommunityTable 1 }

    IpeCfgSnmpCommunityEntry ::= SEQUENCE {
        ipeCfgSnmpCommunityIndex               Integer32,
        ipeCfgSnmpCommunityNEAddress           IpAddress,
        ipeCfgSnmpCommunityName                DisplayString,
        ipeCfgSnmpCommunityAccessLevel         INTEGER,
        ipeCfgSnmpCommunityAccessAddress       IpAddress,
        ipeCfgSnmpCommunityAccessPrefixLength  Integer32,
        ipeCfgSnmpCommunityRowStatus           RowStatus
    }

    ipeCfgSnmpCommunityIndex OBJECT-TYPE
        SYNTAX       Integer32 (1..10)
        MAX-ACCESS   not-accessible
        STATUS       current
        DESCRIPTION  "Index of this table."
        ::= { ipeCfgSnmpCommunityEntry 1 }

    ipeCfgSnmpCommunityNEAddress OBJECT-TYPE
        SYNTAX       IpAddress
        MAX-ACCESS   not-accessible
        STATUS       current
        DESCRIPTION  "reserved."
        ::= { ipeCfgSnmpCommunityEntry 2 }

    ipeCfgSnmpCommunityName OBJECT-TYPE
        SYNTAX       DisplayString (SIZE(1..31))
        MAX-ACCESS   read-create
        STATUS       current
        DESCRIPTION  
            "This entity's community name.
            
            Please use ASCII code.
            
            The characters which can be used are '-', '_','0'-'9', 'a'-'z'
            and 'A'-'Z'."
        ::= { ipeCfgSnmpCommunityEntry 3 }

    ipeCfgSnmpCommunityAccessLevel OBJECT-TYPE
        SYNTAX       INTEGER {
                         invalid(0),
                         operatorLevel(1),
                         configLevel(2),
                         adminLevel(3)
                     }
        MAX-ACCESS   read-create
        STATUS       current
        DESCRIPTION  
            "A access level of a connection using this entry's community
            name."
        ::= { ipeCfgSnmpCommunityEntry 4 }

    ipeCfgSnmpCommunityAccessAddress OBJECT-TYPE
        SYNTAX       IpAddress
        MAX-ACCESS   read-create
        STATUS       current
        DESCRIPTION  
            "An address which is permitted to use this entry's community
            name.
            When masking in ipeCfgSnmpCommunityAccessPrefixLength, the host
            address part has to be a zero, if any.
            
            Also the following address can't be used.
            127.0.0.0/8 Loopback
            224.0.0.0/4 Multicasts (former Class D)
            240.0.0.0/4 Reserved (former Class E)"
        ::= { ipeCfgSnmpCommunityEntry 5 }

    ipeCfgSnmpCommunityAccessPrefixLength OBJECT-TYPE
        SYNTAX       Integer32 (0..32)
        MAX-ACCESS   read-create
        STATUS       current
        DESCRIPTION  "A prefix length of ipeCfgSnmpCommunityAccessAddress."
        ::= { ipeCfgSnmpCommunityEntry 6 }

    ipeCfgSnmpCommunityRowStatus OBJECT-TYPE
        SYNTAX       RowStatus { active(1), createAndGo(4), destroy(6) }
        MAX-ACCESS   read-create
        STATUS       current
        DESCRIPTION  
            "This RowStatus has a status only  active(1).
            You can SET only createAndGo(4) or Destroy(6).
            
            1) how to create
            To create a new row, you must SET objects indicated below.
            
            ipeCfgSnmpCommunityName
            ipeCfgSnmpCommunityAccessLevel
            ipeCfgSnmpCommunityAccessAddress
            ipeCfgSnmpCommunityAccessPrefixLength
            ipeCfgSnmpCommunityAccessAddress2 *
            ipeCfgSnmpCommunityAccessPrefixLength2 *
            ipeCfgSnmpCommunityAccessAddress3 *
            ipeCfgSnmpCommunityAccessPrefixLength3 *
            ipeCfgSnmpCommunityAccessUsage *
            ipeCfgSnmpCommunityAccessUsage2 *
            ipeCfgSnmpCommunityAccessUsage3 *
            ipeCfgSnmpCommunityAccessV6Address
            ipeCfgSnmpCommunityAccessV6PrefixLength
            ipeCfgSnmpCommunityAccessV6Address2 *
            ipeCfgSnmpCommunityAccessV6PrefixLength2 *
            ipeCfgSnmpCommunityAccessV6Address3 *
            ipeCfgSnmpCommunityAccessV6PrefixLength3 *
            ipeCfgSnmpCommunityAccessAddressType *
            ipeCfgSnmpCommunityAccessV6Usage *
            ipeCfgSnmpCommunityAccessV6Usage2 *
            ipeCfgSnmpCommunityAccessV6Usage3 *
            ipeCfgSnmpCommunityRowStatus <- createAndGo(4)
            
            * NOT for EX CPRI
            
            Either ipeCfgSnmpCommunityAccessAddress/Address2/Address3 or 
            ipeCfgSnmpCommunityAccessV6Address/Address2/Address3 can be 
            configured depending on ipeCfgSnmpCommunityAccessAddressType.
            
            ipeCfgSnmpCommunityIndex is an index of this entry.
             
            2) how to destroy
            To destroy a exist row, you must SET a destory(6) to
            ipeCfgSnmpCommunityRowStatus.
            
            3) how to modify
            It is not possible.
            Please destroy a exist row, and create a new row.
            < Attention >
            You have to restart equipment to apply this entry(creating,
            deleting) to actual movement."
        ::= { ipeCfgSnmpCommunityEntry 7 }

    ipeCfgSnmpTrapTable OBJECT-TYPE
        SYNTAX       SEQUENCE OF IpeCfgSnmpTrapEntry
        MAX-ACCESS   not-accessible
        STATUS       current
        DESCRIPTION  "A table of notification information."
        ::= { ipeCfgSnmp 3 }

    ipeCfgSnmpTrapEntry OBJECT-TYPE
        SYNTAX       IpeCfgSnmpTrapEntry
        MAX-ACCESS   not-accessible
        STATUS       current
        DESCRIPTION  "A set of notification information."
        INDEX        { ipeCfgSnmpTrapEntryIndex }
        ::= { ipeCfgSnmpTrapTable 1 }

    IpeCfgSnmpTrapEntry ::= SEQUENCE {
        ipeCfgSnmpTrapEntryIndex      Integer32,
        ipeCfgSnmpTrapEntryNEAddress  IpAddress,
        ipeCfgSnmpTrapVersion         INTEGER,
        ipeCfgSnmpTrapNotifyType      INTEGER,
        ipeCfgSnmpTrapTargetAddress   IpAddress,
        ipeCfgSnmpTrapTargetPort      Integer32,
        ipeCfgSnmpTrapSecurityName    DisplayString,
        ipeCfgSnmpTrapSecurityLevel   INTEGER,
        ipeCfgSnmpTrapEngineId        OCTET STRING,
        ipeCfgSnmpTrapAuthAlgorithm   INTEGER,
        ipeCfgSnmpTrapAuthKey         DisplayString,
        ipeCfgSnmpTrapPrivAlgorithm   INTEGER,
        ipeCfgSnmpTrapPrivKey         DisplayString,
        ipeCfgSnmpTrapRowStatus       RowStatus
    }

    ipeCfgSnmpTrapEntryIndex OBJECT-TYPE
        SYNTAX       Integer32 (1..6)
        MAX-ACCESS   not-accessible
        STATUS       current
        DESCRIPTION  "Index of this table."
        ::= { ipeCfgSnmpTrapEntry 1 }

    ipeCfgSnmpTrapEntryNEAddress OBJECT-TYPE
        SYNTAX       IpAddress
        MAX-ACCESS   not-accessible
        STATUS       current
        DESCRIPTION  "reserved."
        ::= { ipeCfgSnmpTrapEntry 2 }

    ipeCfgSnmpTrapVersion OBJECT-TYPE
        SYNTAX       INTEGER { invalid(0), v1(1), v2c(2), v3(3) }
        MAX-ACCESS   read-create
        STATUS       current
        DESCRIPTION  "A version of this entry's notification."
        ::= { ipeCfgSnmpTrapEntry 3 }

    ipeCfgSnmpTrapNotifyType OBJECT-TYPE
        SYNTAX       INTEGER { invalid(0), trap(1), inform(2) }
        MAX-ACCESS   read-create
        STATUS       current
        DESCRIPTION  "A notification type of this entry's notification."
        ::= { ipeCfgSnmpTrapEntry 4 }

    ipeCfgSnmpTrapTargetAddress OBJECT-TYPE
        SYNTAX       IpAddress
        MAX-ACCESS   read-create
        STATUS       current
        DESCRIPTION  
            "Destination IP address of this entry's notification.
            
            The following address can't be used.
            127.0.0.0/8 Loopback
            0.0.0.0/0    Current network
            224.0.0.0/4 Multicasts (former Class D)
            240.0.0.0/4 Reserved (former Class E)"
        ::= { ipeCfgSnmpTrapEntry 5 }

    ipeCfgSnmpTrapTargetPort OBJECT-TYPE
        SYNTAX       Integer32 (1..65535)
        MAX-ACCESS   read-create
        STATUS       current
        DESCRIPTION  "Destination UDP port this entry's notification."
        ::= { ipeCfgSnmpTrapEntry 6 }

    ipeCfgSnmpTrapSecurityName OBJECT-TYPE
        SYNTAX       DisplayString (SIZE(1..31))
        MAX-ACCESS   read-create
        STATUS       current
        DESCRIPTION  
            "A security name.
            The meaning is different depending on ipeCfgSnmpTrapVersion.
            
            v1/v2c  : It's meaning a community name.
            v3      : It's meaning a user name.
            
            Please use ASCII code.
            
            The characters which can be used are '-', '_','0'-'9', 'a'-'z'
            and 'A'-'Z'.
            
            When there was the same combination to the other index,
            ipeCfgSnmpTrapSecurityName and ipeCfgSnmpTrapEngineId become
            error."
        ::= { ipeCfgSnmpTrapEntry 7 }

    ipeCfgSnmpTrapSecurityLevel OBJECT-TYPE
        SYNTAX       INTEGER {
                         invalid(0),
                         noAuthNoPriv(1),
                         authNoPriv(2),
                         authPriv(3)
                     }
        MAX-ACCESS   read-create
        STATUS       current
        DESCRIPTION  
            "A security level of this entry's notification.
            
            When ipeCfgSnmpTrapVersion is v1(1) or v2c(2), you have to SET
            noAuthNoPriv(1)."
        ::= { ipeCfgSnmpTrapEntry 8 }

    ipeCfgSnmpTrapEngineId OBJECT-TYPE
        SYNTAX       OCTET STRING (SIZE(5..32))
        MAX-ACCESS   read-create
        STATUS       current
        DESCRIPTION  
            "A snmpEngineID which this entry's notification uses.(5-32 octet)
            ipeCfgSnmpTrapNotifyType is effective only at the time of
            inform(2).
            A snmpEngineID of a destination SNMP entity.
            
            When there was the same combination to the other index,
            ipeCfgSnmpTrapSecurityName and ipeCfgSnmpTrapEngineId become
            error."
        ::= { ipeCfgSnmpTrapEntry 9 }

    ipeCfgSnmpTrapAuthAlgorithm OBJECT-TYPE
        SYNTAX       INTEGER { invalid(0), md5(1), sha(2) }
        MAX-ACCESS   read-create
        STATUS       current
        DESCRIPTION  
            "Authentication protocol.
            
            ipeCfgSnmpTrapNotifyType is effective for the SET only at the
            time of inform(2). Even if it is done SET in the case of trap(1),
            I am ignored. In addition, a value of
            ipeCfgAccountUserSnmpV3AuthAlgorithm is acquired at time to get."
        ::= { ipeCfgSnmpTrapEntry 10 }

    ipeCfgSnmpTrapAuthKey OBJECT-TYPE
        SYNTAX       DisplayString (SIZE(8..128))
        MAX-ACCESS   read-create
        STATUS       current
        DESCRIPTION  
            "Authenticate password for SNMP inform PDU.
            This object expects encrypted password by blowfish, not original
            password. Therefore, the size of this object is not same as
            original password size (8..31).
            
            When the object 'ipeCfgSnmpTrapNotifyType' is trap(1), SET
            request is not processed (discarded), and GET request returns the
            same value as 'ipeCfgAccountUserSnmpV3AuthKey'."
        ::= { ipeCfgSnmpTrapEntry 11 }

    ipeCfgSnmpTrapPrivAlgorithm OBJECT-TYPE
        SYNTAX       INTEGER { invalid(0), des(1), aes(2) }
        MAX-ACCESS   read-create
        STATUS       current
        DESCRIPTION  
            "privacy protocol.
            
            ipeCfgSnmpTrapNotifyType is effective for the SET only at the
            time of inform(2). Even if it is done SET in the case of trap(1),
            I am ignored. In addition, a value of
            ipeCfgAccountUserSnmpV3PrivAlgorithm is acquired at time to get."
        ::= { ipeCfgSnmpTrapEntry 12 }

    ipeCfgSnmpTrapPrivKey OBJECT-TYPE
        SYNTAX       DisplayString (SIZE(8..128))
        MAX-ACCESS   read-create
        STATUS       current
        DESCRIPTION  
            "Privacy password for SNMP inform PDU.
            This object expects encrypted password by blowfish, not original
            password. Therefore, the size of this object is not same as
            orignal password size (8..31).
            
            When the object 'ipeCfgSnmpTrapNotifyType' is trap(1), SET
            request is not processed (discarded), and GET request returns the
            same value as 'ipeCfgAccountUserSnmpV3PrivKey'."
        ::= { ipeCfgSnmpTrapEntry 13 }

    ipeCfgSnmpTrapRowStatus OBJECT-TYPE
        SYNTAX       RowStatus { active(1), createAndGo(4), destroy(6) }
        MAX-ACCESS   read-create
        STATUS       current
        DESCRIPTION  
            "This RowStatus has a status only  active(1).
            You can SET only createAndGo(4) or destroy(6).
            
            1) how to create
            1.1) SNMPv1/v2c
            To create a new row, you must SET objects indicated below.
            
            ipeCfgSnmpTrapEntryIndex, ipeCfgSnmpTrapVersion,
            ipeCfgSnmpTrapNotifyType, ipeCfgSnmpTrapTargetAddress,
            ipeCfgSnmpTrapTargetV6Address,
            ipeCfgSnmpTrapTargetAddressType(*), ipeCfgSnmpTrapTaergetPort,
            ipeCfgSnmpTrapSecurityName
            ipeCfgSnmpTrapRowStatus     # Only createAndGo(4).
            
            It isn't necessary to set ipeCfgSnmpTrapSecurityLevel. When set
            it, the value is checked, so all except for noAuthNoPriv (1) will
            be NG.
            And, the other object is not necessary. Even if it is done SET,
            it is checked the value, but ignored.
            
            1.2) SNMPv3 (ipeCfgSnmpTrapNotifyType = trap(1))
            ipeCfgSnmpTrapVersion, ipeCfgSnmpTrapNotifyType,
            ipeCfgSnmpTrapTargetAddress, ipeCfgSnmpTrapTargetV6Address,
            ipeCfgSnmpTrapTargetAddressType(*), ipeCfgSnmpTrapTaergetPort,
            ipeCfgSnmpTrapSecurityName
            ipeCfgSnmpTrapRowStatus     # Only createAndGo(4).
            
            Other object is not necessary. Even if it is done SET, it is
            checked the value, but ignored.
            
            1.3) SNMPv3 (ipeCfgSnmpTrapNotifyType = inform(2))
            To create a new row, you must SET objects indicated below.
            
            ipeCfgSnmpTrapVersion, ipeCfgSnmpTrapNotifyType,
            ipeCfgSnmpTrapTargetAddress, ipeCfgSnmpTrapTargetV6Address,
            ipeCfgSnmpTrapTargetAddressType(*), ipeCfgSnmpTrapTaergetPort,
            ipeCfgSnmpTrapSecurityName, ipeCfgSnmpTrapSecurityLevel,
            ipeCfgSnmpTrapEngineId, ipeCfgSnmpTrapAuthAlgorithm,
            ipeCfgSnmpTrapAuthKey, ipeCfgSnmpTrapPrivAlgorithm,
            ipeCfgSnmpTrapPrivKey
            ipeCfgSnmpTrapRowStatus    # Only createAndGo(4).
            
            * NOT for EX CPRI
            
            ipeCfgSnmpTrapEntryIndex is an index of this entry.
            
            2) how to destroy
            To destroy a exist row, you must SET a destory(6) to
            ipeCfgSnmpCommunityRowStatus.
            
            3) how to modify
            It is not possible.
            Please destroy a exist row, and create a new row."
        ::= { ipeCfgSnmpTrapEntry 14 }

    ipeCfgAccount OBJECT IDENTIFIER
        ::= { ipeConfigurationGroup 12 }

    ipeCfgAccountUserInfoTable OBJECT-TYPE
        SYNTAX       SEQUENCE OF IpeCfgAccountUserInfoEntry
        MAX-ACCESS   not-accessible
        STATUS       current
        DESCRIPTION  "Table of user Information."
        ::= { ipeCfgAccount 1 }

    ipeCfgAccountUserInfoEntry OBJECT-TYPE
        SYNTAX       IpeCfgAccountUserInfoEntry
        MAX-ACCESS   not-accessible
        STATUS       current
        DESCRIPTION  "Entry of user information."
        INDEX        { ipeCfgAccountUserIndex }
        ::= { ipeCfgAccountUserInfoTable 1 }

    IpeCfgAccountUserInfoEntry ::= SEQUENCE {
        ipeCfgAccountUserIndex                Integer32,
        ipeCfgAccountUserNEAddress            IpAddress,
        ipeCfgAccountUserName                 DisplayString,
        ipeCfgAccountUserKey                  DisplayString,
        ipeCfgAccountUserGroup                DisplayString,
        ipeCfgAccountUserSnmpV3SecurityLevel  INTEGER,
        ipeCfgAccountUserSnmpV3AuthAlgorithm  INTEGER,
        ipeCfgAccountUserSnmpV3AuthKey        DisplayString,
        ipeCfgAccountUserSnmpV3PrivAlgorithm  INTEGER,
        ipeCfgAccountUserSnmpV3PrivKey        DisplayString,
        ipeCfgAccountUserRowStatus            RowStatus
    }

    ipeCfgAccountUserIndex OBJECT-TYPE
        SYNTAX       Integer32 (1..102)
        MAX-ACCESS   not-accessible
        STATUS       current
        DESCRIPTION  "Index of this table."
        ::= { ipeCfgAccountUserInfoEntry 1 }

    ipeCfgAccountUserNEAddress OBJECT-TYPE
        SYNTAX       IpAddress
        MAX-ACCESS   not-accessible
        STATUS       current
        DESCRIPTION  "reserved."
        ::= { ipeCfgAccountUserInfoEntry 2 }

    ipeCfgAccountUserName OBJECT-TYPE
        SYNTAX       DisplayString (SIZE(1..31))
        MAX-ACCESS   read-create
        STATUS       current
        DESCRIPTION  
            "User Name.
            An overlap of a user name isn't permitted.
            
            Please use ASCII code.
            
            The characters which can be used are '-', '_','0'-'9', 'a'-'z'
            and 'A'-'Z'."
        ::= { ipeCfgAccountUserInfoEntry 3 }

    ipeCfgAccountUserKey OBJECT-TYPE
        SYNTAX       DisplayString (SIZE(8..128))
        MAX-ACCESS   read-create
        STATUS       current
        DESCRIPTION  
            "User password encrypted by blowfish.
            Acceptable characters for this object is shown below.
            
            '-', '_','0'-'9', 'a'-'z' and 'A'-'Z'."
        ::= { ipeCfgAccountUserInfoEntry 4 }

    ipeCfgAccountUserGroup OBJECT-TYPE
        SYNTAX       DisplayString (SIZE(1..31))
        MAX-ACCESS   read-create
        STATUS       current
        DESCRIPTION  
            "This object defines the privilege for the user.
            Acceptable characters for this object is shown below.
            
            '-', '_','0'-'9', 'a'-'z' and 'A'-'Z'."
        ::= { ipeCfgAccountUserInfoEntry 5 }

    ipeCfgAccountUserSnmpV3SecurityLevel OBJECT-TYPE
        SYNTAX       INTEGER {
                         invalid(0),
                         noAuthNoPriv(1),
                         authNoPriv(2),
                         authPriv(3)
                     }
        MAX-ACCESS   read-create
        STATUS       current
        DESCRIPTION  
            "SNMPv3 security level.
            
            Setting for SET/GET/TRAP at the time of the SNMPv3 use(INFORM is
            inapplicable)"
        ::= { ipeCfgAccountUserInfoEntry 6 }

    ipeCfgAccountUserSnmpV3AuthAlgorithm OBJECT-TYPE
        SYNTAX       INTEGER { invalid(0), md5(1), sha(2) }
        MAX-ACCESS   read-create
        STATUS       current
        DESCRIPTION  
            "Hash calculate algorithm of authenticate password.
            
            Setting for SET/GET/TRAP at the time of the SNMPv3 use(INFORM is
            inapplicable)"
        ::= { ipeCfgAccountUserInfoEntry 7 }

    ipeCfgAccountUserSnmpV3AuthKey OBJECT-TYPE
        SYNTAX       DisplayString (SIZE(8..128))
        MAX-ACCESS   read-create
        STATUS       current
        DESCRIPTION  
            "Authenticate password for SNMP SET/GET/TRAP PDU.
            This object expects encrypted password by blowfish, not original
            password. Therefore, the size of this object is not same as
            orignal password (8..31).
            
            When the object 'ipeCfgSnmpTrapNotifyType' is set to inform(2),
            the INFORM PDU Authenticate key is configured by
            'ipeCfgSnmpTrapAuthKey'."
        ::= { ipeCfgAccountUserInfoEntry 8 }

    ipeCfgAccountUserSnmpV3PrivAlgorithm OBJECT-TYPE
        SYNTAX       INTEGER { invalid(0), des(1), aes(2) }
        MAX-ACCESS   read-create
        STATUS       current
        DESCRIPTION  
            "Cipher algorithm.
            
            Setting for SET/GET/TRAP at the time of the SNMPv3 use(INFORM is
            inapplicable)"
        ::= { ipeCfgAccountUserInfoEntry 9 }

    ipeCfgAccountUserSnmpV3PrivKey OBJECT-TYPE
        SYNTAX       DisplayString (SIZE(8..128))
        MAX-ACCESS   read-create
        STATUS       current
        DESCRIPTION  
            "Privacy password for SNMP SET/GET/TRAP PDU.
            This object expects encrypted password by blowfish, not original
            password. Therefore, the size of this object is not same as
            orignal password (8..31).
            
            When the 'ipeCfgSnmpTrapNotifyType' is set to inform(2), the
            INFORM PDU Authenticate key is configured by
            'ipeCfgSnmpTrapAuthKey'."
        ::= { ipeCfgAccountUserInfoEntry 10 }

    ipeCfgAccountUserRowStatus OBJECT-TYPE
        SYNTAX       RowStatus { active(1), createAndGo(4), destroy(6) }
        MAX-ACCESS   read-create
        STATUS       current
        DESCRIPTION  
            "This RowStatus has a status only active(1). 
            
            1) creating a entry
            When you make a new entry, you must SET objects indicated below.
            
            ipeCfgAccountUserIndex
            ipeCfgAccountUserName
            ipeCfgAccountUserKey
            ipeCfgAccountUserGroup
            ipeCfgAccountUserSnmpV3SecurityLevel
            ipeCfgAccountUserSnmpV3AuthAlgorithm
            ipeCfgAccountUserSnmpV3AuthKey
            ipeCfgAccountUserSnmpV3PrivAlgorithm
            ipeCfgAccountUserSnmpV3PrivKey
            ipeCfgAccountUserRowStatus <- createAndGo(4)
            
            2) modifing a entry
            ipeCfgAccountUserKey can only be changed.
            Other items can not be updated. Please do destroy of entry and a
            create.
            
            3) deleting a entry
            When you SET a destroy(6) to ipeCfgAccountUserRowStatus, the
            entry is destroyed.
            
            4) About SNMPv3
            When there is not ipeCfgAccountGroupInfoEntry corresponding to
            ipeCfgAccountUserGroup, SNMPv3-TRAP which I used
            ipeCfgAccountUserName for is output, but cannot use
            SNMPv3-Set/Get-Request."
        ::= { ipeCfgAccountUserInfoEntry 11 }

    ipeCfgAccountGroupInfoTable OBJECT-TYPE
        SYNTAX       SEQUENCE OF IpeCfgAccountGroupInfoEntry
        MAX-ACCESS   not-accessible
        STATUS       current
        DESCRIPTION  "Table of Group Information."
        ::= { ipeCfgAccount 2 }

    ipeCfgAccountGroupInfoEntry OBJECT-TYPE
        SYNTAX       IpeCfgAccountGroupInfoEntry
        MAX-ACCESS   not-accessible
        STATUS       current
        DESCRIPTION  "Entry of Group Information."
        INDEX        { ipeCfgAccountGroupIndex }
        ::= { ipeCfgAccountGroupInfoTable 1 }

    IpeCfgAccountGroupInfoEntry ::= SEQUENCE {
        ipeCfgAccountGroupIndex        Integer32,
        ipeCfgAccountGroupNEAddress    IpAddress,
        ipeCfgAccountGroupName         DisplayString,
        ipeCfgAccountGroupTelnet       INTEGER,
        ipeCfgAccountGroupSsh          INTEGER,
        ipeCfgAccountGroupFtp          INTEGER,
        ipeCfgAccountGroupSftp         INTEGER,
        ipeCfgAccountGroupHttp         INTEGER,
        ipeCfgAccountGroupHttps        INTEGER,
        ipeCfgAccountGroupSnmp         INTEGER,
        ipeCfgAccountGroupAccessLevel  INTEGER,
        ipeCfgAccountGroupRowStatus    RowStatus
    }

    ipeCfgAccountGroupIndex OBJECT-TYPE
        SYNTAX       Integer32 (1..10)
        MAX-ACCESS   not-accessible
        STATUS       current
        DESCRIPTION  "Index of this table."
        ::= { ipeCfgAccountGroupInfoEntry 1 }

    ipeCfgAccountGroupNEAddress OBJECT-TYPE
        SYNTAX       IpAddress
        MAX-ACCESS   not-accessible
        STATUS       current
        DESCRIPTION  "reserved."
        ::= { ipeCfgAccountGroupInfoEntry 2 }

    ipeCfgAccountGroupName OBJECT-TYPE
        SYNTAX       DisplayString (SIZE(1..31))
        MAX-ACCESS   read-create
        STATUS       current
        DESCRIPTION  
            "Group name.
            An overlap of a group name isn't permitted.
            
            Please use ASCII code.
            
            The characters which can be used are '-', '_','0'-'9', 'a'-'z'
            and 'A'-'Z'."
        ::= { ipeCfgAccountGroupInfoEntry 3 }

    ipeCfgAccountGroupTelnet OBJECT-TYPE
        SYNTAX       INTEGER { invalid(0), disabled(1), enabled(2) }
        MAX-ACCESS   read-create
        STATUS       current
        DESCRIPTION  "TELNET enable."
        ::= { ipeCfgAccountGroupInfoEntry 4 }

    ipeCfgAccountGroupSsh OBJECT-TYPE
        SYNTAX       INTEGER { invalid(0), disabled(1), enabled(2) }
        MAX-ACCESS   read-create
        STATUS       current
        DESCRIPTION  "SSH enable."
        ::= { ipeCfgAccountGroupInfoEntry 5 }

    ipeCfgAccountGroupFtp OBJECT-TYPE
        SYNTAX       INTEGER { invalid(0), disabled(1), enabled(2) }
        MAX-ACCESS   read-create
        STATUS       current
        DESCRIPTION  "FTP enable."
        ::= { ipeCfgAccountGroupInfoEntry 6 }

    ipeCfgAccountGroupSftp OBJECT-TYPE
        SYNTAX       INTEGER { invalid(0), disabled(1), enabled(2) }
        MAX-ACCESS   read-create
        STATUS       current
        DESCRIPTION  "SFTP enable."
        ::= { ipeCfgAccountGroupInfoEntry 7 }

    ipeCfgAccountGroupHttp OBJECT-TYPE
        SYNTAX       INTEGER { invalid(0), disabled(1), enabled(2) }
        MAX-ACCESS   read-create
        STATUS       current
        DESCRIPTION  "HTTP enable."
        ::= { ipeCfgAccountGroupInfoEntry 8 }

    ipeCfgAccountGroupHttps OBJECT-TYPE
        SYNTAX       INTEGER { invalid(0), disabled(1), enabled(2) }
        MAX-ACCESS   read-create
        STATUS       current
        DESCRIPTION  "HTTPS enable."
        ::= { ipeCfgAccountGroupInfoEntry 9 }

    ipeCfgAccountGroupSnmp OBJECT-TYPE
        SYNTAX       INTEGER { invalid(0), disabled(1), enabled(2) }
        MAX-ACCESS   read-create
        STATUS       current
        DESCRIPTION  "SNMP enable."
        ::= { ipeCfgAccountGroupInfoEntry 10 }

    ipeCfgAccountGroupAccessLevel OBJECT-TYPE
        SYNTAX       INTEGER {
                         invalid(0),
                         operatorLevel(1),
                         configLevel(2),
                         adminLevel(3)
                     }
        MAX-ACCESS   read-create
        STATUS       current
        DESCRIPTION  "Access level."
        ::= { ipeCfgAccountGroupInfoEntry 11 }

    ipeCfgAccountGroupRowStatus OBJECT-TYPE
        SYNTAX       RowStatus { active(1), createAndGo(4), destroy(6) }
        MAX-ACCESS   read-create
        STATUS       current
        DESCRIPTION  
            "This RowStatus has a status only 'active(1)'. 
            
            1) creating a entry.
            When you make a new entry, you must SET objects indicated below.
            
            ipeCfgAccountGroupName
            ipeCfgAccountGroupTelnet
            ipeCfgAccountGroupSsh
            ipeCfgAccountGroupFtp
            ipeCfgAccountGroupSftp
            ipeCfgAccountGroupHttp
            ipeCfgAccountGroupHttps
            ipeCfgAccountGroupSnmp
            ipeCfgAccountGroupAccessLevel
            ipeCfgAccountGroupRowStatus <- createAndGo(4)
            
            ipeCfgAccountGroupIndex is an index of this entry.
            
            2) deleting a entry.
            When you SET a destroy(6) to ipeCfgAccountGroupRowStatus, the
            entry is destroyed.
            
            Information that synchronizes and is deleted:
             User Information setting(ssh/ftp/http login information)
             SNMPv3-Set/Get-Req user info
            (The SNMPv3-TRAP information is left)
            
            3) modifing a entry
            It can change it other than ipeCfgAccountGroupName,
            ipeCfgAccountGroupRowStatus.
            But the entry of default (ADMIN/OPERATOR/CONFIG) is impossible of
            a change ipeCfgAccountGroupName."
        ::= { ipeCfgAccountGroupInfoEntry 12 }

    ipeCfgUserAccountAuthTable OBJECT-TYPE
        SYNTAX       SEQUENCE OF IpeCfgUserAccountAuthEntry
        MAX-ACCESS   not-accessible
        STATUS       current
        DESCRIPTION  "Configure user authentication method about Web LCT."
        ::= { ipeCfgAccount 4 }

    ipeCfgUserAccountAuthEntry OBJECT-TYPE
        SYNTAX       IpeCfgUserAccountAuthEntry
        MAX-ACCESS   not-accessible
        STATUS       current
        DESCRIPTION  "..."
        INDEX        { ipeCfgUserAccountAuthIndex }
        ::= { ipeCfgUserAccountAuthTable 1 }

    IpeCfgUserAccountAuthEntry ::= SEQUENCE {
        ipeCfgUserAccountAuthIndex         Integer32,
        ipeCfgUserAccountAuthNEAddress     IpAddress,
        ipeCfgUserAccountAuthMode          INTEGER,
        ipeCfgUserAccountAuthOrder         INTEGER,
        ipeCfgUserAccountAuthTrapEnable    INTEGER,
        ipeCfgUserAccountAuthTrapLocal     INTEGER,
        ipeCfgUserAccountAuthTrapExternal  INTEGER
    }

    ipeCfgUserAccountAuthIndex OBJECT-TYPE
        SYNTAX       Integer32 (1..1)
        MAX-ACCESS   not-accessible
        STATUS       current
        DESCRIPTION  "Index of this table."
        ::= { ipeCfgUserAccountAuthEntry 1 }

    ipeCfgUserAccountAuthNEAddress OBJECT-TYPE
        SYNTAX       IpAddress
        MAX-ACCESS   not-accessible
        STATUS       current
        DESCRIPTION  "Reserved object for northbound interface."
        ::= { ipeCfgUserAccountAuthEntry 2 }

    ipeCfgUserAccountAuthMode OBJECT-TYPE
        SYNTAX       INTEGER { invalid(0), mode1(1), mode2(2), mode3(3) }
        MAX-ACCESS   read-write
        STATUS       current
        DESCRIPTION  
            "Indicate the user authentication mode.
            
            mode1 : local authentication only.
            mode2 : local and LDAP authentication. (NOT SUPPORTED)
            mode3 : local and RADIUS authentication. 
            
            mode2 will be supprted in future version."
        DEFVAL       { mode1 }
        ::= { ipeCfgUserAccountAuthEntry 3 }

    ipeCfgUserAccountAuthOrder OBJECT-TYPE
        SYNTAX       INTEGER {
                         invalid(0),
                         localAuthFirst(1),
                         externalAuthFirst(2)
                     }
        MAX-ACCESS   read-write
        STATUS       current
        DESCRIPTION  
            "Indicate the user authentication order.
            This object is effective only if ipeCfgUserAccountAuthMode
            is set to mode2 or mode3.
            External authentication means authentication with RADIUS or
            LDAP.
            
            localAuthFirst    : local -> external
            externalAuthFirst : external -> local"
        DEFVAL       { localAuthFirst }
        ::= { ipeCfgUserAccountAuthEntry 4 }

    ipeCfgUserAccountAuthTrapEnable OBJECT-TYPE
        SYNTAX       INTEGER { invalid(0), disable(1), enable(2) }
        MAX-ACCESS   read-write
        STATUS       current
        DESCRIPTION  
            "Enable or disable user login trap.
            In case this object is set to enable, the system sends trap
            when user attempt to login to Web LCT."
        DEFVAL       { enable }
        ::= { ipeCfgUserAccountAuthEntry 5 }

    ipeCfgUserAccountAuthTrapLocal OBJECT-TYPE
        SYNTAX       INTEGER { invalid(0), success(1), failure(2) }
        MAX-ACCESS   read-only
        STATUS       current
        DESCRIPTION  
            "Indicate authentication result of local authentication.
            This object is dedicated for login control trap.
            If you read this object, the system returns invalid(0)."
        DEFVAL       { invalid }
        ::= { ipeCfgUserAccountAuthEntry 6 }

    ipeCfgUserAccountAuthTrapExternal OBJECT-TYPE
        SYNTAX       INTEGER { invalid(0), success(1), failure(2) }
        MAX-ACCESS   read-only
        STATUS       current
        DESCRIPTION  
            "Indicate authentication result of externel authentication.
            This object is dedicated for login control trap.
            If you read this object, the system returns invalid(0)."
        DEFVAL       { invalid }
        ::= { ipeCfgUserAccountAuthEntry 7 }

    ipeCfgDhcpGroup OBJECT IDENTIFIER
        ::= { ipeConfigurationGroup 13 }

    ipeCfgDhcpServerTable OBJECT-TYPE
        SYNTAX       SEQUENCE OF IpeCfgDhcpServerEntry
        MAX-ACCESS   not-accessible
        STATUS       current
        DESCRIPTION  "DHCPserver table."
        ::= { ipeCfgDhcpGroup 1 }

    ipeCfgDhcpServerEntry OBJECT-TYPE
        SYNTAX       IpeCfgDhcpServerEntry
        MAX-ACCESS   not-accessible
        STATUS       current
        DESCRIPTION  "entry of DHCPserver table."
        INDEX        { ipeCfgDhcpServerIndex }
        ::= { ipeCfgDhcpServerTable 1 }

    IpeCfgDhcpServerEntry ::= SEQUENCE {
        ipeCfgDhcpServerIndex          Integer32,
        ipeCfgDhcpServerNEAddress      IpAddress,
        ipeCfgDhcpServerEnable         INTEGER,
        ipeCfgDhcpLeaseAddrRangeBegin  IpAddress,
        ipeCfgDhcpLeaseAddrRangeEnd    IpAddress
    }

    ipeCfgDhcpServerIndex OBJECT-TYPE
        SYNTAX       Integer32 (1..2)
        MAX-ACCESS   not-accessible
        STATUS       current
        DESCRIPTION  "Index of this table."
        ::= { ipeCfgDhcpServerEntry 1 }

    ipeCfgDhcpServerNEAddress OBJECT-TYPE
        SYNTAX       IpAddress
        MAX-ACCESS   not-accessible
        STATUS       current
        DESCRIPTION  "reserved."
        ::= { ipeCfgDhcpServerEntry 2 }

    ipeCfgDhcpServerEnable OBJECT-TYPE
        SYNTAX       INTEGER { start(1), stop(2), restart(3) }
        MAX-ACCESS   read-write
        STATUS       current
        DESCRIPTION  
            "Effective/invalid setting of DHCP.
            value range:start(1)
                        stop(2)
                        restart(3)
            DHCPD has already started. When the start is specified, DHCPD
            restart."
        ::= { ipeCfgDhcpServerEntry 3 }

    ipeCfgDhcpLeaseAddrRangeBegin OBJECT-TYPE
        SYNTAX       IpAddress
        MAX-ACCESS   read-write
        STATUS       current
        DESCRIPTION  
            "Beginning IPaddress within the range of lease address.
            value range:Dotted decimal notation
            denial value:0.0.0.0 , 127.0.0.1 , 255.255.255.255
            ipeCfgDhcpLeaseAddrRangeBegin don't same as
            ipeCfgPortLctIpAddress value"
        ::= { ipeCfgDhcpServerEntry 4 }

    ipeCfgDhcpLeaseAddrRangeEnd OBJECT-TYPE
        SYNTAX       IpAddress
        MAX-ACCESS   read-write
        STATUS       current
        DESCRIPTION  
            "End IPaddress within the range of lease address.
            value range:Dotted decimal notation
            denial value:0.0.0.0 , 127.0.0.1 , 255.255.255.255
            ipeCfgDhcpLeaseAddrRangeEnd don't same as ipeCfgPortLctIpAddress
            value"
        ::= { ipeCfgDhcpServerEntry 5 }

    ipeCfgStpGroup OBJECT IDENTIFIER
        ::= { ipeConfigurationGroup 14 }

    ipeCfgStpBridgeTable OBJECT-TYPE
        SYNTAX       SEQUENCE OF IpeCfgStpBridgeEntry
        MAX-ACCESS   not-accessible
        STATUS       current
        DESCRIPTION  "STP state setting table."
        ::= { ipeCfgStpGroup 1 }

    ipeCfgStpBridgeEntry OBJECT-TYPE
        SYNTAX       IpeCfgStpBridgeEntry
        MAX-ACCESS   not-accessible
        STATUS       current
        DESCRIPTION  "entry of STP state setting table."
        INDEX        { ipeCfgStpBridgeIndex }
        ::= { ipeCfgStpBridgeTable 1 }

    IpeCfgStpBridgeEntry ::= SEQUENCE {
        ipeCfgStpBridgeIndex         Integer32,
        ipeCfgStpBridgeNEAddress     IpAddress,
        ipeCfgStpEnable              INTEGER,
        ipeCfgStpPriority            Integer32,
        ipeCfgStpBridgeMaxAge        Timeout,
        ipeCfgStpBridgeHelloTime     Timeout,
        ipeCfgStpBridgeForwardDelay  Timeout
    }

    ipeCfgStpBridgeIndex OBJECT-TYPE
        SYNTAX       Integer32 (1..20)
        MAX-ACCESS   not-accessible
        STATUS       current
        DESCRIPTION  "Index of this table."
        ::= { ipeCfgStpBridgeEntry 1 }

    ipeCfgStpBridgeNEAddress OBJECT-TYPE
        SYNTAX       IpAddress
        MAX-ACCESS   not-accessible
        STATUS       current
        DESCRIPTION  "reserved."
        ::= { ipeCfgStpBridgeEntry 2 }

    ipeCfgStpEnable OBJECT-TYPE
        SYNTAX       INTEGER { enabled(1), disabled(2) }
        MAX-ACCESS   read-write
        STATUS       current
        DESCRIPTION  
            "Effective/invalid setting of STP.
            value :enabled
                   disabled"
        ::= { ipeCfgStpBridgeEntry 3 }

    ipeCfgStpPriority OBJECT-TYPE
        SYNTAX       Integer32 (0..65535)
        MAX-ACCESS   read-write
        STATUS       current
        DESCRIPTION  
            "Bridge priority.
            value range:0 to 65535"
        ::= { ipeCfgStpBridgeEntry 4 }

    ipeCfgStpBridgeMaxAge OBJECT-TYPE
        SYNTAX       Timeout (600..4000)
        MAX-ACCESS   read-write
        STATUS       current
        DESCRIPTION  
            "MaxAge (in units of hundredths of a second).
            value range:600 to 4000
            rule: 2 * (ipeCfgStpBridgeForwardDelay - 1) =>
            ipeCfgStpBridgeMaxAge
                 ipeCfgStpBridgeMaxAge >= 2 * (ipeCfgStpBridgeHelloTime + 1)"
        ::= { ipeCfgStpBridgeEntry 5 }

    ipeCfgStpBridgeHelloTime OBJECT-TYPE
        SYNTAX       Timeout (100..1000)
        MAX-ACCESS   read-write
        STATUS       current
        DESCRIPTION  
            "HelloTime (in units of hundredths of a second).
            value range:100 to 1000
            rule:ipeCfgStpBridgeMaxAge >= 2x(ipeCfgStpBridgeHelloTime + 1)"
        ::= { ipeCfgStpBridgeEntry 6 }

    ipeCfgStpBridgeForwardDelay OBJECT-TYPE
        SYNTAX       Timeout (400..3000)
        MAX-ACCESS   read-write
        STATUS       current
        DESCRIPTION  
            "ForwardDelay (in units of hundredths of a second).
            value range:400 to 3000
            rule: 2 * (ipeCfgStpBridgeForwardDelay - 1) >=
            ipeCfgStpBridgeMaxAge"
        ::= { ipeCfgStpBridgeEntry 7 }

    ipeCfgStpPortTable OBJECT-TYPE
        SYNTAX       SEQUENCE OF IpeCfgStpPortEntry
        MAX-ACCESS   not-accessible
        STATUS       current
        DESCRIPTION  "STP port information table."
        ::= { ipeCfgStpGroup 2 }

    ipeCfgStpPortEntry OBJECT-TYPE
        SYNTAX       IpeCfgStpPortEntry
        MAX-ACCESS   not-accessible
        STATUS       current
        DESCRIPTION  "entry of  STP port information table."
        INDEX        { ipeCfgStpPortIfIndex }
        ::= { ipeCfgStpPortTable 1 }

    IpeCfgStpPortEntry ::= SEQUENCE {
        ipeCfgStpPortIfIndex     InterfaceIndex,
        ipeCfgStpPortNEAddress   IpAddress,
        ipeCfgStpPortPriority    Integer32,
        ipeCfgStpPortPathCost    Integer32,
        ipeCfgStpPortEdgeEnable  INTEGER
    }

    ipeCfgStpPortIfIndex OBJECT-TYPE
        SYNTAX       InterfaceIndex
        MAX-ACCESS   not-accessible
        STATUS       current
        DESCRIPTION  "Index of this table."
        ::= { ipeCfgStpPortEntry 1 }

    ipeCfgStpPortNEAddress OBJECT-TYPE
        SYNTAX       IpAddress
        MAX-ACCESS   not-accessible
        STATUS       current
        DESCRIPTION  "reserved."
        ::= { ipeCfgStpPortEntry 2 }

    ipeCfgStpPortPriority OBJECT-TYPE
        SYNTAX       Integer32 (0..63)
        MAX-ACCESS   read-write
        STATUS       current
        DESCRIPTION  
            "Port priority.
            value range:0 to 63"
        ::= { ipeCfgStpPortEntry 3 }

    ipeCfgStpPortPathCost OBJECT-TYPE
        SYNTAX       Integer32 (1..65535)
        MAX-ACCESS   read-write
        STATUS       current
        DESCRIPTION  
            "Pathcost.
            value range:1 to 65535"
        ::= { ipeCfgStpPortEntry 4 }

    ipeCfgStpPortEdgeEnable OBJECT-TYPE
        SYNTAX       INTEGER { enabled(1), disabled(2) }
        MAX-ACCESS   read-write
        STATUS       current
        DESCRIPTION  
            "Effective/invalid setting of BPDU.
            value range:enabled(1)
                        disabled(2)"
        ::= { ipeCfgStpPortEntry 5 }

    ipeCfgPortGroup OBJECT IDENTIFIER
        ::= { ipeConfigurationGroup 15 }

    ipeCfgPortModemTable OBJECT-TYPE
        SYNTAX       SEQUENCE OF IpeCfgPortModemEntry
        MAX-ACCESS   not-accessible
        STATUS       current
        DESCRIPTION  "MODEM port set up information table."
        ::= { ipeCfgPortGroup 1 }

    ipeCfgPortModemEntry OBJECT-TYPE
        SYNTAX       IpeCfgPortModemEntry
        MAX-ACCESS   not-accessible
        STATUS       current
        DESCRIPTION  "entry of  MODEM port set up information table."
        INDEX        { ipeCfgPortModemIfIndex }
        ::= { ipeCfgPortModemTable 1 }

    IpeCfgPortModemEntry ::= SEQUENCE {
        ipeCfgPortModemIfIndex    InterfaceIndex,
        ipeCfgPortModemNEAddress  IpAddress,
        ipeCfgPortModemEnable     INTEGER
    }

    ipeCfgPortModemIfIndex OBJECT-TYPE
        SYNTAX       InterfaceIndex
        MAX-ACCESS   not-accessible
        STATUS       current
        DESCRIPTION  "Index of this table."
        ::= { ipeCfgPortModemEntry 1 }

    ipeCfgPortModemNEAddress OBJECT-TYPE
        SYNTAX       IpAddress
        MAX-ACCESS   not-accessible
        STATUS       current
        DESCRIPTION  "reserved."
        ::= { ipeCfgPortModemEntry 2 }

    ipeCfgPortModemEnable OBJECT-TYPE
        SYNTAX       INTEGER { enabled(1), disabled(2) }
        MAX-ACCESS   read-write
        STATUS       current
        DESCRIPTION  
            "Effective/invalid setting of MODEM port.
            value range: enabled(1)
                        disabled(2)"
        ::= { ipeCfgPortModemEntry 3 }

    ipeCfgPortLctTable OBJECT-TYPE
        SYNTAX       SEQUENCE OF IpeCfgPortLctEntry
        MAX-ACCESS   not-accessible
        STATUS       current
        DESCRIPTION  "LCT port set up information table."
        ::= { ipeCfgPortGroup 2 }

    ipeCfgPortLctEntry OBJECT-TYPE
        SYNTAX       IpeCfgPortLctEntry
        MAX-ACCESS   not-accessible
        STATUS       current
        DESCRIPTION  "entry of  LCT port set up information table."
        INDEX        { ipeCfgPortLctIfIndex }
        ::= { ipeCfgPortLctTable 1 }

    IpeCfgPortLctEntry ::= SEQUENCE {
        ipeCfgPortLctIfIndex    InterfaceIndex,
        ipeCfgPortLctNEAddress  IpAddress,
        ipeCfgPortLctIpAddress  IpAddress,
        ipeCfgPortLctNetMask    IpAddress,
        ipeCfgPortLctEnable     INTEGER,
        ipeCfgPortLctMtu        Integer32,
        ipeCfgPortLctAutoNeg    INTEGER
    }

    ipeCfgPortLctIfIndex OBJECT-TYPE
        SYNTAX       InterfaceIndex
        MAX-ACCESS   not-accessible
        STATUS       current
        DESCRIPTION  "Index of this table."
        ::= { ipeCfgPortLctEntry 1 }

    ipeCfgPortLctNEAddress OBJECT-TYPE
        SYNTAX       IpAddress
        MAX-ACCESS   not-accessible
        STATUS       current
        DESCRIPTION  "reserved."
        ::= { ipeCfgPortLctEntry 2 }

    ipeCfgPortLctIpAddress OBJECT-TYPE
        SYNTAX       IpAddress
        MAX-ACCESS   read-write
        STATUS       current
        DESCRIPTION  
            "IPaddress of LCT port.
            It makes an error of the Internet Protocol address setting that
            overlaps in the port in the device.
            The object port and the range of the value are described as
            follows.
            Object port: Lct, InbandMngVLAN1-16, Bridge1-Bridge20, NE2
            Value range:0x00000000-0xdfffffff(0.0.0.0-223.255.255.255)
            The relation is not in the state and the number of Branch of
            interfaces and the Internet Protocol address repetition check is
            checked.
            
            When 0.0.0.0 is set to ipeCfgPortLctIpAddress, it becomes an
            Internet Protocol address deletion."
        ::= { ipeCfgPortLctEntry 3 }

    ipeCfgPortLctNetMask OBJECT-TYPE
        SYNTAX       IpAddress
        MAX-ACCESS   read-write
        STATUS       current
        DESCRIPTION  
            "Subnet mask of LCT port.
            When it isn't proper as subnetmask, it'll be an error.
            Value range:0x00000000-0xfffffffc(0-30bit)"
        ::= { ipeCfgPortLctEntry 4 }

    ipeCfgPortLctEnable OBJECT-TYPE
        SYNTAX       INTEGER { enabled(1), disabled(2) }
        MAX-ACCESS   read-write
        STATUS       current
        DESCRIPTION  
            "Effective/invalid setting of LCT port.
            value range: enabled
                        disabled"
        ::= { ipeCfgPortLctEntry 5 }

    ipeCfgPortLctMtu OBJECT-TYPE
        SYNTAX       Integer32 (256..1500)
        MAX-ACCESS   read-write
        STATUS       current
        DESCRIPTION  
            "MTU value of LCT.
            value range:256 to 1500"
        ::= { ipeCfgPortLctEntry 6 }

    ipeCfgPortLctAutoNeg OBJECT-TYPE
        SYNTAX       INTEGER { enabled(1), disabled(2) }
        MAX-ACCESS   read-write
        STATUS       current
        DESCRIPTION  
            "Effective/invalid setting of LCT AUTO NEGOTIATION.
            value range: enabled
                        disabled"
        ::= { ipeCfgPortLctEntry 7 }

    ipeCfgPortEtherTable OBJECT-TYPE
        SYNTAX       SEQUENCE OF IpeCfgPortEtherEntry
        MAX-ACCESS   not-accessible
        STATUS       current
        DESCRIPTION  "NMS/NE1 port set up information table."
        ::= { ipeCfgPortGroup 3 }

    ipeCfgPortEtherEntry OBJECT-TYPE
        SYNTAX       IpeCfgPortEtherEntry
        MAX-ACCESS   not-accessible
        STATUS       current
        DESCRIPTION  "entry of  NMS/NE1 port set up information table."
        INDEX        { ipeCfgPortEtherIfIndex }
        ::= { ipeCfgPortEtherTable 1 }

    IpeCfgPortEtherEntry ::= SEQUENCE {
        ipeCfgPortEtherIfIndex        InterfaceIndex,
        ipeCfgPortEtherNEAddress      IpAddress,
        ipeCfgPortEtherEnable         INTEGER,
        ipeCfgPortEtherAutoNeg        INTEGER,
        ipeCfgPortEtherSpecialFilter  INTEGER,
        ipeCfgPortEtherLldpMode       INTEGER
    }

    ipeCfgPortEtherIfIndex OBJECT-TYPE
        SYNTAX       InterfaceIndex
        MAX-ACCESS   not-accessible
        STATUS       current
        DESCRIPTION  "Index of this table."
        ::= { ipeCfgPortEtherEntry 1 }

    ipeCfgPortEtherNEAddress OBJECT-TYPE
        SYNTAX       IpAddress
        MAX-ACCESS   not-accessible
        STATUS       current
        DESCRIPTION  "reserved."
        ::= { ipeCfgPortEtherEntry 2 }

    ipeCfgPortEtherEnable OBJECT-TYPE
        SYNTAX       INTEGER { enabled(1), disabled(2) }
        MAX-ACCESS   read-write
        STATUS       current
        DESCRIPTION  
            "Effective/invalid setting of NMS/NE1 port.
            value range: enabled(1)
                        disabled(2)"
        DEFVAL       { enabled }
        ::= { ipeCfgPortEtherEntry 3 }

    ipeCfgPortEtherAutoNeg OBJECT-TYPE
        SYNTAX       INTEGER { enabled(1), disabled(2) }
        MAX-ACCESS   read-write
        STATUS       current
        DESCRIPTION  
            "Auto negotiation invalid effective/setting of NMS/NE1 port.
            value range: enabled(1)
                        disabled(2)"
        ::= { ipeCfgPortEtherEntry 4 }

    ipeCfgPortEtherSpecialFilter OBJECT-TYPE
        SYNTAX       INTEGER { true(1), false(2) }
        MAX-ACCESS   read-write
        STATUS       current
        DESCRIPTION  
            "Setting of whether a special broadcast packet is blocked."
        ::= { ipeCfgPortEtherEntry 5 }

    ipeCfgPortEtherLldpMode OBJECT-TYPE
        SYNTAX       INTEGER { invalid(0), standardMode(1), proprietaryMode(2) }
        MAX-ACCESS   read-write
        STATUS       current
        DESCRIPTION  
            "Switch to select MAC address of LLDP Frame.
            
              standardMode    : MAC address of LLDP Frame is 
                                01-80-C2-00-00-0E.
              proprietaryMode : MAC address of LLDP Frame is configured in 
                                ipeCfgLldpProprietaryModeMacAddress."
        DEFVAL       { standardMode }
        ::= { ipeCfgPortEtherEntry 6 }

    ipeCfgPortNe2Table OBJECT-TYPE
        SYNTAX       SEQUENCE OF IpeCfgPortNe2Entry
        MAX-ACCESS   not-accessible
        STATUS       current
        DESCRIPTION  "NE2 port set up information table."
        ::= { ipeCfgPortGroup 4 }

    ipeCfgPortNe2Entry OBJECT-TYPE
        SYNTAX       IpeCfgPortNe2Entry
        MAX-ACCESS   not-accessible
        STATUS       current
        DESCRIPTION  "entry of NE2 port set up information table."
        INDEX        { ipeCfgPortNe2IfIndex }
        ::= { ipeCfgPortNe2Table 1 }

    IpeCfgPortNe2Entry ::= SEQUENCE {
        ipeCfgPortNe2IfIndex            InterfaceIndex,
        ipeCfgPortNe2NEAddress          IpAddress,
        ipeCfgPortNe2IpAddress          IpAddress,
        ipeCfgPortNe2Enable             INTEGER,
        ipeCfgPortNe2Speed              INTEGER,
        ipeCfgPortNe2NeighborMibEnable  INTEGER
    }

    ipeCfgPortNe2IfIndex OBJECT-TYPE
        SYNTAX       InterfaceIndex
        MAX-ACCESS   not-accessible
        STATUS       current
        DESCRIPTION  "Index of this table."
        ::= { ipeCfgPortNe2Entry 1 }

    ipeCfgPortNe2NEAddress OBJECT-TYPE
        SYNTAX       IpAddress
        MAX-ACCESS   not-accessible
        STATUS       current
        DESCRIPTION  "reserved."
        ::= { ipeCfgPortNe2Entry 2 }

    ipeCfgPortNe2IpAddress OBJECT-TYPE
        SYNTAX       IpAddress
        MAX-ACCESS   read-write
        STATUS       current
        DESCRIPTION  
            "NE2 port IP Address.
            value range:0x00000000 - 0xdfffffff(0.0.0.0 - 223.255.255.255)
            The ppp function is restarted when setting it."
        ::= { ipeCfgPortNe2Entry 3 }

    ipeCfgPortNe2Enable OBJECT-TYPE
        SYNTAX       INTEGER { enabled(1), disabled(2) }
        MAX-ACCESS   read-write
        STATUS       current
        DESCRIPTION  
            "NE2 port enable.
            value range:enabled(1)
                        disabled(2)"
        ::= { ipeCfgPortNe2Entry 4 }

    ipeCfgPortNe2Speed OBJECT-TYPE
        SYNTAX       INTEGER { speed9600(9600), speed19200(19200) }
        MAX-ACCESS   read-write
        STATUS       current
        DESCRIPTION  
            "NE2 port baud rate.
            value range:9600bps(9600)
                        19200bps(19200)
            The ppp function is restarted when setting it."
        ::= { ipeCfgPortNe2Entry 5 }

    ipeCfgPortNe2NeighborMibEnable OBJECT-TYPE
        SYNTAX       INTEGER { enabled(1), disabled(2) }
        MAX-ACCESS   read-write
        STATUS       current
        DESCRIPTION  
            "NE2 port neighbor detection enable.
            value range:enabled(1)
                        disabled(2)
            The ppp function is restarted when setting it."
        ::= { ipeCfgPortNe2Entry 6 }

    ipeCfgPortE1Table OBJECT-TYPE
        SYNTAX       SEQUENCE OF IpeCfgPortE1Entry
        MAX-ACCESS   not-accessible
        STATUS       current
        DESCRIPTION  "E1 port set up information table."
        ::= { ipeCfgPortGroup 5 }

    ipeCfgPortE1Entry OBJECT-TYPE
        SYNTAX       IpeCfgPortE1Entry
        MAX-ACCESS   not-accessible
        STATUS       current
        DESCRIPTION  "entry of  E1 port set up information table."
        INDEX        { ipeCfgPortE1IfIndex }
        ::= { ipeCfgPortE1Table 1 }

    IpeCfgPortE1Entry ::= SEQUENCE {
        ipeCfgPortE1IfIndex        InterfaceIndex,
        ipeCfgPortE1NEAddress      IpAddress,
        ipeCfgPortE1Enable         INTEGER,
        ipeCfgPortE1ChannelNumber  Integer32
    }

    ipeCfgPortE1IfIndex OBJECT-TYPE
        SYNTAX       InterfaceIndex
        MAX-ACCESS   not-accessible
        STATUS       current
        DESCRIPTION  "Index of this table."
        ::= { ipeCfgPortE1Entry 1 }

    ipeCfgPortE1NEAddress OBJECT-TYPE
        SYNTAX       IpAddress
        MAX-ACCESS   not-accessible
        STATUS       current
        DESCRIPTION  "reserved."
        ::= { ipeCfgPortE1Entry 2 }

    ipeCfgPortE1Enable OBJECT-TYPE
        SYNTAX       INTEGER { enabled(1), disabled(2) }
        MAX-ACCESS   read-write
        STATUS       current
        DESCRIPTION  
            "Effective/invalid setting of E1 port.
            value range: enabled(1)
                        disabled(2)"
        ::= { ipeCfgPortE1Entry 3 }

    ipeCfgPortE1ChannelNumber OBJECT-TYPE
        SYNTAX       Integer32 (1..16)
        MAX-ACCESS   read-write
        STATUS       current
        DESCRIPTION  
            "Use channel of E1 port.
            value range:1 to 16"
        ::= { ipeCfgPortE1Entry 4 }

    ipeCfgPortInbandTable OBJECT-TYPE
        SYNTAX       SEQUENCE OF IpeCfgPortInbandEntry
        MAX-ACCESS   not-accessible
        STATUS       current
        DESCRIPTION  
            "InBand Management VLAN port set up information table."
        ::= { ipeCfgPortGroup 6 }

    ipeCfgPortInbandEntry OBJECT-TYPE
        SYNTAX       IpeCfgPortInbandEntry
        MAX-ACCESS   not-accessible
        STATUS       current
        DESCRIPTION  
            "entry of  INBAND Management VLAN port set up information table."
        INDEX        { ipeCfgPortInbandIfIndex }
        ::= { ipeCfgPortInbandTable 1 }

    IpeCfgPortInbandEntry ::= SEQUENCE {
        ipeCfgPortInbandIfIndex    InterfaceIndex,
        ipeCfgPortInbandNEAddress  IpAddress,
        ipeCfgPortInbandIpAddress  IpAddress,
        ipeCfgPortInbandNetMask    IpAddress,
        ipeCfgPortInbandEnable     INTEGER,
        ipeCfgPortInbandVlanId     Integer32,
        ipeCfgPortInbandMtu        Integer32,
        ipeCfgPortInbandCos        Integer32
    }

    ipeCfgPortInbandIfIndex OBJECT-TYPE
        SYNTAX       InterfaceIndex
        MAX-ACCESS   not-accessible
        STATUS       current
        DESCRIPTION  "Index of this table."
        ::= { ipeCfgPortInbandEntry 1 }

    ipeCfgPortInbandNEAddress OBJECT-TYPE
        SYNTAX       IpAddress
        MAX-ACCESS   not-accessible
        STATUS       current
        DESCRIPTION  "reserved."
        ::= { ipeCfgPortInbandEntry 2 }

    ipeCfgPortInbandIpAddress OBJECT-TYPE
        SYNTAX       IpAddress
        MAX-ACCESS   read-write
        STATUS       obsolete
        DESCRIPTION  
            "IPaddress of INBAND Management VLAN port.
            It makes an error of the Internet Protocol address setting that
            overlaps in the port in the device.
            The object port and the range of the value are described as
            follows.
            Object port: Lct, InbandMngVLAN1-16, Bridge1-20, NE2
            Value range: 0x00000000 - 0xdfffffff(0.0.0.0 - 223.255.255.255)
            The relation is not in the state and the number of Branch of
            interfaces and the Internet Protocol address repetition check is
            checked.
            
            When 0.0.0.0 is set to ipeCfgPortInbandIpAddress, it becomes an
            Internet Protocol address deletion."
        ::= { ipeCfgPortInbandEntry 3 }

    ipeCfgPortInbandNetMask OBJECT-TYPE
        SYNTAX       IpAddress
        MAX-ACCESS   read-write
        STATUS       obsolete
        DESCRIPTION  
            "Subnet mask of INBAND Management VLAN port.
            When it isn't proper as subnetmask, it'll be an error.
            Value range:0x00000000 - 0xfffffffc(0 - 30bit)"
        ::= { ipeCfgPortInbandEntry 4 }

    ipeCfgPortInbandEnable OBJECT-TYPE
        SYNTAX       INTEGER { enabled(1), disabled(2) }
        MAX-ACCESS   read-write
        STATUS       current
        DESCRIPTION  
            "Effective/invalid setting of INBAND Management VLAN port.
            value range: enabled(1)
                        disabled(2)"
        ::= { ipeCfgPortInbandEntry 5 }

    ipeCfgPortInbandVlanId OBJECT-TYPE
        SYNTAX       Integer32 (1..4094)
        MAX-ACCESS   read-write
        STATUS       current
        DESCRIPTION  
            "VLAN ID of INBAND Management VLAN port.
            value range:1 to 4094"
        ::= { ipeCfgPortInbandEntry 6 }

    ipeCfgPortInbandMtu OBJECT-TYPE
        SYNTAX       Integer32 (256..1500)
        MAX-ACCESS   read-write
        STATUS       obsolete
        DESCRIPTION  
            "MTU value of INBAND Management VLAN port.
            value range:256 to 1500"
        ::= { ipeCfgPortInbandEntry 7 }

    ipeCfgPortInbandCos OBJECT-TYPE
        SYNTAX       Integer32 (0..7)
        MAX-ACCESS   read-write
        STATUS       current
        DESCRIPTION  "CoS value of INBAND Management VLAN port"
        DEFVAL       { 7 }
        ::= { ipeCfgPortInbandEntry 8 }

    ipeCfgPortMainEtherTable OBJECT-TYPE
        SYNTAX       SEQUENCE OF IpeCfgPortMainEtherEntry
        MAX-ACCESS   not-accessible
        STATUS       current
        DESCRIPTION  "Main traffic ether port set up information table."
        ::= { ipeCfgPortGroup 7 }

    ipeCfgPortMainEtherEntry OBJECT-TYPE
        SYNTAX       IpeCfgPortMainEtherEntry
        MAX-ACCESS   not-accessible
        STATUS       current
        DESCRIPTION  
            "entry of main traffic ether port set up information table."
        INDEX        { ipeCfgPortMainEtherIfIndex }
        ::= { ipeCfgPortMainEtherTable 1 }

    IpeCfgPortMainEtherEntry ::= SEQUENCE {
        ipeCfgPortMainEtherIfIndex    InterfaceIndex,
        ipeCfgPortMainEtherNEAddress  IpAddress,
        ipeCfgPortMainEtherLldpMode   INTEGER
    }

    ipeCfgPortMainEtherIfIndex OBJECT-TYPE
        SYNTAX       InterfaceIndex
        MAX-ACCESS   not-accessible
        STATUS       current
        DESCRIPTION  "Index of this table."
        ::= { ipeCfgPortMainEtherEntry 1 }

    ipeCfgPortMainEtherNEAddress OBJECT-TYPE
        SYNTAX       IpAddress
        MAX-ACCESS   not-accessible
        STATUS       current
        DESCRIPTION  "reserved."
        ::= { ipeCfgPortMainEtherEntry 2 }

    ipeCfgPortMainEtherLldpMode OBJECT-TYPE
        SYNTAX       INTEGER { invalid(0), standardMode(1), proprietaryMode(2) }
        MAX-ACCESS   read-write
        STATUS       current
        DESCRIPTION  
            "Switch to select MAC address of LLDP Frame.
                         
            standardMode    : MAC address of LLDP Frame is 01-80-C2-00-00-0E.
            proprietaryMode : MAC address of LLDP Frame is configured in 
                              ipeCfgLldpProprietaryModeMacAddress."
        DEFVAL       { standardMode }
        ::= { ipeCfgPortMainEtherEntry 3 }

    ipeCfgBridgeGroup OBJECT IDENTIFIER
        ::= { ipeConfigurationGroup 16 }

    ipeCfgBridgeTable OBJECT-TYPE
        SYNTAX       SEQUENCE OF IpeCfgBridgeEntry
        MAX-ACCESS   not-accessible
        STATUS       current
        DESCRIPTION  "Bridge set up information table."
        ::= { ipeCfgBridgeGroup 1 }

    ipeCfgBridgeEntry OBJECT-TYPE
        SYNTAX       IpeCfgBridgeEntry
        MAX-ACCESS   not-accessible
        STATUS       current
        DESCRIPTION  "entry of  Bridge set up information table."
        INDEX        { ipeCfgBridgeIndex }
        ::= { ipeCfgBridgeTable 1 }

    IpeCfgBridgeEntry ::= SEQUENCE {
        ipeCfgBridgeIndex      Integer32,
        ipeCfgBridgeNEAddress  IpAddress,
        ipeCfgBridgeIpAddress  IpAddress,
        ipeCfgBridgeNetMask    IpAddress,
        ipeCfgBridgeMtu        Integer32
    }

    ipeCfgBridgeIndex OBJECT-TYPE
        SYNTAX       Integer32 (1..20)
        MAX-ACCESS   not-accessible
        STATUS       current
        DESCRIPTION  "Index of this table."
        ::= { ipeCfgBridgeEntry 1 }

    ipeCfgBridgeNEAddress OBJECT-TYPE
        SYNTAX       IpAddress
        MAX-ACCESS   not-accessible
        STATUS       current
        DESCRIPTION  "reserved."
        ::= { ipeCfgBridgeEntry 2 }

    ipeCfgBridgeIpAddress OBJECT-TYPE
        SYNTAX       IpAddress
        MAX-ACCESS   read-write
        STATUS       current
        DESCRIPTION  
            "IPAddress set to bridge.
            Value range:0x00000000 - 0xdfffffff(0.0.0.0 - 223.255.255.255)
            
            It makes an error of the Internet Protocol address setting that
            overlaps in the port in the device.
            It becomes the following about the port of the Internet Protocol
            address repetition check object.
            Object port: Lct, InbandMngVLAN1-16, Bridge1-Bridge20, NE2
            The relation is not in the state and the number of Branch of
            interfaces and the Internet Protocol address repetition check is
            checked.
            
            There can not be relation and it sets, and it refer the number of
            branch.
            When 0.0.0.0 is set to ipeCfgBridgeIpAddress, it becomes an
            Internet Protocol address deletion."
        ::= { ipeCfgBridgeEntry 3 }

    ipeCfgBridgeNetMask OBJECT-TYPE
        SYNTAX       IpAddress
        MAX-ACCESS   read-write
        STATUS       current
        DESCRIPTION  
            "Netmask set to bridge.
            When it isn't proper as subnetmask, it'll be an error.
            Value range:0x00000000 - 0xfffffffc(0 - 30bit)
            
            There can not be relation and it sets, and it refer the number of
            branch."
        ::= { ipeCfgBridgeEntry 4 }

    ipeCfgBridgeMtu OBJECT-TYPE
        SYNTAX       Integer32 (256..1500)
        MAX-ACCESS   read-write
        STATUS       current
        DESCRIPTION  
            "MTU value of bridge.
            value range:256 to 1500
            
            There can not be relation and it sets, and it refer the number of
            branch."
        ::= { ipeCfgBridgeEntry 5 }

    ipeCfgBridgePortTable OBJECT-TYPE
        SYNTAX       SEQUENCE OF IpeCfgBridgePortEntry
        MAX-ACCESS   not-accessible
        STATUS       current
        DESCRIPTION  "Bridge set up information table."
        ::= { ipeCfgBridgeGroup 2 }

    ipeCfgBridgePortEntry OBJECT-TYPE
        SYNTAX       IpeCfgBridgePortEntry
        MAX-ACCESS   not-accessible
        STATUS       current
        DESCRIPTION  "entry of  Bridge set up information table."
        INDEX        { ipeCfgBridgePortIfIndex }
        ::= { ipeCfgBridgePortTable 1 }

    IpeCfgBridgePortEntry ::= SEQUENCE {
        ipeCfgBridgePortIfIndex      InterfaceIndex,
        ipeCfgBridgePortNEAddress    IpAddress,
        ipeCfgBridgePortBridgeIndex  Integer32
    }

    ipeCfgBridgePortIfIndex OBJECT-TYPE
        SYNTAX       InterfaceIndex
        MAX-ACCESS   not-accessible
        STATUS       current
        DESCRIPTION  "Index of this table."
        ::= { ipeCfgBridgePortEntry 1 }

    ipeCfgBridgePortNEAddress OBJECT-TYPE
        SYNTAX       IpAddress
        MAX-ACCESS   not-accessible
        STATUS       current
        DESCRIPTION  "reserved."
        ::= { ipeCfgBridgePortEntry 2 }

    ipeCfgBridgePortBridgeIndex OBJECT-TYPE
        SYNTAX       Integer32 (0..20)
        MAX-ACCESS   read-write
        STATUS       current
        DESCRIPTION  "Index value of bridge."
        ::= { ipeCfgBridgePortEntry 3 }

    ipeCfgPripGroup OBJECT IDENTIFIER
        ::= { ipeConfigurationGroup 17 }

    ipeCfgPripTable OBJECT-TYPE
        SYNTAX       SEQUENCE OF IpeCfgPripEntry
        MAX-ACCESS   not-accessible
        STATUS       current
        DESCRIPTION  "PRIP set up information table."
        ::= { ipeCfgPripGroup 1 }

    ipeCfgPripEntry OBJECT-TYPE
        SYNTAX       IpeCfgPripEntry
        MAX-ACCESS   not-accessible
        STATUS       current
        DESCRIPTION  "entry of PRIP set up information table."
        INDEX        { ipeCfgPripIndex }
        ::= { ipeCfgPripTable 1 }

    IpeCfgPripEntry ::= SEQUENCE {
        ipeCfgPripIndex        Integer32,
        ipeCfgPripNEAddress    IpAddress,
        ipeCfgPripRouteEnable  INTEGER,
        ipeCfgPripUdpPort      INTEGER
    }

    ipeCfgPripIndex OBJECT-TYPE
        SYNTAX       Integer32 (1..1)
        MAX-ACCESS   not-accessible
        STATUS       current
        DESCRIPTION  "Index of this table."
        ::= { ipeCfgPripEntry 1 }

    ipeCfgPripNEAddress OBJECT-TYPE
        SYNTAX       IpAddress
        MAX-ACCESS   not-accessible
        STATUS       current
        DESCRIPTION  "reserved."
        ::= { ipeCfgPripEntry 2 }

    ipeCfgPripRouteEnable OBJECT-TYPE
        SYNTAX       INTEGER { invalid(0), enabled(1), disabled(2) }
        MAX-ACCESS   read-write
        STATUS       current
        DESCRIPTION  
            "Enable or disables PRIP.
            
            enabled(1):PRIP is enabled. 
            disabled(2):PRIP is disabled."
        ::= { ipeCfgPripEntry 3 }

    ipeCfgPripUdpPort OBJECT-TYPE
        SYNTAX       INTEGER { ripdefaultport(520), pripdefaultport(8520) }
        MAX-ACCESS   read-write
        STATUS       current
        DESCRIPTION  
            "Setting of UDP port number used with PRIP.
            
            Either of 8520 or 520 is set.
            
            This setting is valid since PRIP will start next time."
        ::= { ipeCfgPripEntry 4 }

    ipeCfgPripPortTable OBJECT-TYPE
        SYNTAX       SEQUENCE OF IpeCfgPripPortEntry
        MAX-ACCESS   not-accessible
        STATUS       current
        DESCRIPTION  "PRIP set up information table.(per port)"
        ::= { ipeCfgPripGroup 2 }

    ipeCfgPripPortEntry OBJECT-TYPE
        SYNTAX       IpeCfgPripPortEntry
        MAX-ACCESS   not-accessible
        STATUS       current
        DESCRIPTION  "entry of PRIP set up information table.(per port)"
        INDEX        { ipeCfgPripPortIfIndex }
        ::= { ipeCfgPripPortTable 1 }

    IpeCfgPripPortEntry ::= SEQUENCE {
        ipeCfgPripPortIfIndex             InterfaceIndex,
        ipeCfgPripPortNEAddress           IpAddress,
        ipeCfgPripPortEnable              INTEGER,
        ipeCfgPripPortPropagateNetEnable  INTEGER
    }

    ipeCfgPripPortIfIndex OBJECT-TYPE
        SYNTAX       InterfaceIndex
        MAX-ACCESS   not-accessible
        STATUS       current
        DESCRIPTION  "Index of this table."
        ::= { ipeCfgPripPortEntry 1 }

    ipeCfgPripPortNEAddress OBJECT-TYPE
        SYNTAX       IpAddress
        MAX-ACCESS   not-accessible
        STATUS       current
        DESCRIPTION  "reserved."
        ::= { ipeCfgPripPortEntry 2 }

    ipeCfgPripPortEnable OBJECT-TYPE
        SYNTAX       INTEGER { invalid(0), enabled(1), disabled(2) }
        MAX-ACCESS   read-write
        STATUS       current
        DESCRIPTION  
            "Setting of some port when PRIP will be enabled.
            
            enabled(1)  : this port is enabled.
            disabled(2) : this port is disable."
        ::= { ipeCfgPripPortEntry 3 }

    ipeCfgPripPortPropagateNetEnable OBJECT-TYPE
        SYNTAX       INTEGER { invalid(0), enabled(1), disabled(2) }
        MAX-ACCESS   read-write
        STATUS       current
        DESCRIPTION  
            "Propagate setting for neighbor NE.
            
            enabled(1)  : this port is propagated.
            disabled(2) : this port is not propagated.
                          (Do not register in the RIP route.)"
        ::= { ipeCfgPripPortEntry 4 }

    ipeCfgNaptGroup OBJECT IDENTIFIER
        ::= { ipeConfigurationGroup 18 }

    ipeCfgNaptTable OBJECT-TYPE
        SYNTAX       SEQUENCE OF IpeCfgNaptEntry
        MAX-ACCESS   not-accessible
        STATUS       current
        DESCRIPTION  "NAPT set up information table."
        ::= { ipeCfgNaptGroup 1 }

    ipeCfgNaptEntry OBJECT-TYPE
        SYNTAX       IpeCfgNaptEntry
        MAX-ACCESS   not-accessible
        STATUS       current
        DESCRIPTION  "entry of  NAPT set up information table."
        INDEX        { ipeCfgNaptIndex }
        ::= { ipeCfgNaptTable 1 }

    IpeCfgNaptEntry ::= SEQUENCE {
        ipeCfgNaptIndex      Integer32,
        ipeCfgNaptNEAddress  IpAddress,
        ipeCfgNaptEnable     INTEGER
    }

    ipeCfgNaptIndex OBJECT-TYPE
        SYNTAX       Integer32 (1..1)
        MAX-ACCESS   not-accessible
        STATUS       current
        DESCRIPTION  "Index of this table."
        ::= { ipeCfgNaptEntry 1 }

    ipeCfgNaptNEAddress OBJECT-TYPE
        SYNTAX       IpAddress
        MAX-ACCESS   not-accessible
        STATUS       current
        DESCRIPTION  "reserved."
        ::= { ipeCfgNaptEntry 2 }

    ipeCfgNaptEnable OBJECT-TYPE
        SYNTAX       INTEGER { enabled(1), disabled(2) }
        MAX-ACCESS   read-write
        STATUS       current
        DESCRIPTION  
            "Address translation invalid effective/setting by NAPT.
            value range: enabled
                        disabled"
        ::= { ipeCfgNaptEntry 3 }

    ipeCfgStaticRouteGroup OBJECT IDENTIFIER
        ::= { ipeConfigurationGroup 19 }

    ipeCfgStaticRouteTable OBJECT-TYPE
        SYNTAX       SEQUENCE OF IpeCfgStaticRouteEntry
        MAX-ACCESS   not-accessible
        STATUS       current
        DESCRIPTION  "Static Routing set up information table."
        ::= { ipeCfgStaticRouteGroup 1 }

    ipeCfgStaticRouteEntry OBJECT-TYPE
        SYNTAX       IpeCfgStaticRouteEntry
        MAX-ACCESS   not-accessible
        STATUS       current
        DESCRIPTION  "entry of  Static Routing set up information table."
        INDEX        { ipeCfgRouteIndex }
        ::= { ipeCfgStaticRouteTable 1 }

    IpeCfgStaticRouteEntry ::= SEQUENCE {
        ipeCfgRouteIndex      Integer32,
        ipeCfgRouteNEAddress  IpAddress,
        ipeCfgRouteDest       IpAddress,
        ipeCfgRouteMask       IpAddress,
        ipeCfgRouteNextHop    IpAddress,
        ipeCfgRouteRowStatus  RowStatus
    }

    ipeCfgRouteIndex OBJECT-TYPE
        SYNTAX       Integer32 (1..128)
        MAX-ACCESS   not-accessible
        STATUS       current
        DESCRIPTION  "Index of this table."
        ::= { ipeCfgStaticRouteEntry 1 }

    ipeCfgRouteNEAddress OBJECT-TYPE
        SYNTAX       IpAddress
        MAX-ACCESS   not-accessible
        STATUS       current
        DESCRIPTION  "reserved."
        ::= { ipeCfgStaticRouteEntry 2 }

    ipeCfgRouteDest OBJECT-TYPE
        SYNTAX       IpAddress
        MAX-ACCESS   read-create
        STATUS       current
        DESCRIPTION  
            "Static routing object destination address.
            When masking in ipeCfgRouteMask, the host address part has to be
            a zero, if any.
            Value range:0x00000000-0xdfffffff(0.0.0.0-223.255.255.255)
            The value acquisition when unsetting it returns NoSuchObject."
        ::= { ipeCfgStaticRouteEntry 3 }

    ipeCfgRouteMask OBJECT-TYPE
        SYNTAX       IpAddress
        MAX-ACCESS   read-create
        STATUS       current
        DESCRIPTION  
            "Static routing object subnet mask.
            When it isn't proper as subnetmask, it'll be an error.
            Value range:0x00000000-0xffffffff(0-32bit)
            Only when ipeCfgRouteDest is 0, 0bit is allowed.
            The value acquisition when unsetting it returns NoSuchObject."
        ::= { ipeCfgStaticRouteEntry 4 }

    ipeCfgRouteNextHop OBJECT-TYPE
        SYNTAX       IpAddress
        MAX-ACCESS   read-create
        STATUS       current
        DESCRIPTION  
            "Static routing object gateway address.
            Value range:0x00000001 - 0xdfffffff(0.0.0.1 - 223.255.255.255)
            The value acquisition when unsetting it returns NoSuchObject."
        ::= { ipeCfgStaticRouteEntry 5 }

    ipeCfgRouteRowStatus OBJECT-TYPE
        SYNTAX       RowStatus { active(1), createAndGo(4), destroy(6) }
        MAX-ACCESS   read-create
        STATUS       current
        DESCRIPTION  
            "This RowStatus has a status only 'active(1)'. 
            
            1) creating a entry
            When you make a new entry, you must SET objects indicated below.
            * ipeCfgRouteDest
            * ipeCfgRouteMask
            * ipeCfgRouteNextHop
            * ipeCfgRouteRowStatus <- createAndGo(4)
            
            2) modifing a entry
            When you make a existing entry, you must SET objects indicated
            below.
            * ipeCfgRouteDest
            * ipeCfgRouteMask
            * ipeCfgRouteNextHop
            
            3) deleting a entry
            When you SET a destroy(6) to ipeCfgRouteRowStatus, the entry is
            destroyed.
            * ipeCfgRouteRowStatus <- destory(6)"
        ::= { ipeCfgStaticRouteEntry 6 }

    ipeCfgAccessListGroup OBJECT IDENTIFIER
        ::= { ipeConfigurationGroup 21 }

    ipeCfgAccessListRuleTable OBJECT-TYPE
        SYNTAX       SEQUENCE OF IpeCfgAccessListRuleEntry
        MAX-ACCESS   not-accessible
        STATUS       current
        DESCRIPTION  "Table of Access List(Rule)."
        ::= { ipeCfgAccessListGroup 1 }

    ipeCfgAccessListRuleEntry OBJECT-TYPE
        SYNTAX       IpeCfgAccessListRuleEntry
        MAX-ACCESS   not-accessible
        STATUS       current
        DESCRIPTION  "Entry of Access List(Rule)."
        INDEX        { ipeCfgAccessListRuleEnableIndex }
        ::= { ipeCfgAccessListRuleTable 1 }

    IpeCfgAccessListRuleEntry ::= SEQUENCE {
        ipeCfgAccessListRuleEnableIndex       Integer32,
        ipeCfgAccessListRuleNEAddress         IpAddress,
        ipeCfgAccessListInputRuleEnable       INTEGER,
        ipeCfgAccessListForwardRuleEnable     INTEGER,
        ipeCfgAccessListInputDefaultAction    INTEGER,
        ipeCfgAccessListForwardDefaultAction  INTEGER
    }

    ipeCfgAccessListRuleEnableIndex OBJECT-TYPE
        SYNTAX       Integer32 (1..1)
        MAX-ACCESS   not-accessible
        STATUS       current
        DESCRIPTION  "Index of this table."
        ::= { ipeCfgAccessListRuleEntry 1 }

    ipeCfgAccessListRuleNEAddress OBJECT-TYPE
        SYNTAX       IpAddress
        MAX-ACCESS   not-accessible
        STATUS       current
        DESCRIPTION  "reserved."
        ::= { ipeCfgAccessListRuleEntry 2 }

    ipeCfgAccessListInputRuleEnable OBJECT-TYPE
        SYNTAX       INTEGER { invalid(0), disable(1), enable(2) }
        MAX-ACCESS   read-write
        STATUS       current
        DESCRIPTION  "IP Access Control Input Filter Rule"
        ::= { ipeCfgAccessListRuleEntry 3 }

    ipeCfgAccessListForwardRuleEnable OBJECT-TYPE
        SYNTAX       INTEGER { invalid(0), disable(1), enable(2) }
        MAX-ACCESS   read-write
        STATUS       current
        DESCRIPTION  "IP Access Control Forwarding Filter Rule"
        ::= { ipeCfgAccessListRuleEntry 4 }

    ipeCfgAccessListInputDefaultAction OBJECT-TYPE
        SYNTAX       INTEGER { permit(1), deny(2) }
        MAX-ACCESS   read-write
        STATUS       current
        DESCRIPTION  "IP Access Control Input Default Action."
        ::= { ipeCfgAccessListRuleEntry 5 }

    ipeCfgAccessListForwardDefaultAction OBJECT-TYPE
        SYNTAX       INTEGER { permit(1), deny(2) }
        MAX-ACCESS   read-write
        STATUS       current
        DESCRIPTION  "IP Access Control Forwarding Default Action"
        ::= { ipeCfgAccessListRuleEntry 6 }

    ipeCfgAccessListInputTable OBJECT-TYPE
        SYNTAX       SEQUENCE OF IpeCfgAccessListInputEntry
        MAX-ACCESS   not-accessible
        STATUS       current
        DESCRIPTION  "Table of Access List(Input Direction)."
        ::= { ipeCfgAccessListGroup 2 }

    ipeCfgAccessListInputEntry OBJECT-TYPE
        SYNTAX       IpeCfgAccessListInputEntry
        MAX-ACCESS   not-accessible
        STATUS       current
        DESCRIPTION  "Entry of Access List(Input Direction)."
        INDEX        { ipeCfgAccessListInputOrderNum }
        ::= { ipeCfgAccessListInputTable 1 }

    IpeCfgAccessListInputEntry ::= SEQUENCE {
        ipeCfgAccessListInputOrderNum      Integer32,
        ipeCfgAccessListInputNEAddress     IpAddress,
        ipeCfgAccessListInputInIfIndex     INTEGER,
        ipeCfgAccessListInputSrcIpAddress  IpAddress,
        ipeCfgAccessListInputSrcNetMask    IpAddress,
        ipeCfgAccessListInputProtocol      Integer32,
        ipeCfgAccessListInputDstPortNum    Integer32,
        ipeCfgAccessListInputAction        INTEGER,
        ipeCfgAccessListInputRowStatus     RowStatus
    }

    ipeCfgAccessListInputOrderNum OBJECT-TYPE
        SYNTAX       Integer32 (1..50)
        MAX-ACCESS   not-accessible
        STATUS       current
        DESCRIPTION  "Index of table(1-50)."
        ::= { ipeCfgAccessListInputEntry 1 }

    ipeCfgAccessListInputNEAddress OBJECT-TYPE
        SYNTAX       IpAddress
        MAX-ACCESS   not-accessible
        STATUS       current
        DESCRIPTION  "reserved."
        ::= { ipeCfgAccessListInputEntry 2 }

    ipeCfgAccessListInputInIfIndex OBJECT-TYPE
        SYNTAX       INTEGER {
                         any(0),
                         inband(3),
                         ne2(4),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Input Filter Interface.
            
            The value 'inband' is not supported."
        ::= { ipeCfgAccessListInputEntry 3 }

    ipeCfgAccessListInputSrcIpAddress OBJECT-TYPE
        SYNTAX       IpAddress
        MAX-ACCESS   read-create
        STATUS       current
        DESCRIPTION  "IP Access Control Input Filter Source IP Address"
        ::= { ipeCfgAccessListInputEntry 4 }

    ipeCfgAccessListInputSrcNetMask OBJECT-TYPE
        SYNTAX       IpAddress
        MAX-ACCESS   read-create
        STATUS       current
        DESCRIPTION  
            "IP Access Control Input Filter Source Subnet Mask.
            '0.0.0.0' matches all IP addresses. i.e. '0.0.0.0' acts as
            'Any'."
        ::= { ipeCfgAccessListInputEntry 5 }

    ipeCfgAccessListInputProtocol OBJECT-TYPE
        SYNTAX       Integer32
        MAX-ACCESS   read-create
        STATUS       current
        DESCRIPTION  
            "IP Access Control Input Filter Protocol.
            '-1' acts as 'Any'."
        ::= { ipeCfgAccessListInputEntry 6 }

    ipeCfgAccessListInputDstPortNum OBJECT-TYPE
        SYNTAX       Integer32
        MAX-ACCESS   read-create
        STATUS       current
        DESCRIPTION  
            "IP Access Control Input Filter Port Number.
            '-1' acts as 'Any'."
        ::= { ipeCfgAccessListInputEntry 7 }

    ipeCfgAccessListInputAction OBJECT-TYPE
        SYNTAX       INTEGER { permit(1), deny(2) }
        MAX-ACCESS   read-create
        STATUS       current
        DESCRIPTION  "IP Access Control Input Filter Action."
        ::= { ipeCfgAccessListInputEntry 8 }

    ipeCfgAccessListInputRowStatus OBJECT-TYPE
        SYNTAX       RowStatus { active(1), createAndGo(4), destroy(6) }
        MAX-ACCESS   read-create
        STATUS       current
        DESCRIPTION  
            "This RowStatus has a status only 'active(1)'. 
            
            1) creating a entry
            When you make a new entry, you must SET objects indicated below.
            ipeCfgAccessListInputAction
            ipeCfgAccessListInputRowStatus <- createAndGo(4)
            
            
            When you are not setting a value of items as follows, it is set
            as 'any'.
            ipeCfgAccessListInputInIfIndex
            ipeCfgAccessListInputSrcIpAddress
            ipeCfgAccessListInputSrcNetMask(*1)
            ipeCfgAccessListInputProtocol
            ipeCfgAccessListInputDstPortNum(*2)
            
            *1 When you not set ipeCfgAccessListInputSrcIpAddress, even when
            ipeCfgAccessListInputSrcNetMask is set, it is set as 'any'.When
            ipeCfgAccessListInputSrcIpAddress set to 'any',
            ipeCfgAccessListInputSrcNetMask is set as 'any'.
            *2 When you not set ipeCfgAccessListInputProtocol to '6' or '17',
            even when ipeCfgAccessListInputDstPortNum is set, it is set as
            'any'.
            
            2) modifing a entry
            It isn't possible.
            
            3) deleting a entry
            When you SET a destroy(6) to ipeCfgAccessListInputRowStatus, the
            entry is destroyed."
        ::= { ipeCfgAccessListInputEntry 9 }

    ipeCfgAccessListForwardTable OBJECT-TYPE
        SYNTAX       SEQUENCE OF IpeCfgAccessListForwardEntry
        MAX-ACCESS   not-accessible
        STATUS       current
        DESCRIPTION  "Table of Access List(Forward Direction)."
        ::= { ipeCfgAccessListGroup 3 }

    ipeCfgAccessListForwardEntry OBJECT-TYPE
        SYNTAX       IpeCfgAccessListForwardEntry
        MAX-ACCESS   not-accessible
        STATUS       current
        DESCRIPTION  "Entry of Access List(Forward Direction)."
        INDEX        { ipeCfgAccessListForwardOrderNum }
        ::= { ipeCfgAccessListForwardTable 1 }

    IpeCfgAccessListForwardEntry ::= SEQUENCE {
        ipeCfgAccessListForwardOrderNum      Integer32,
        ipeCfgAccessListForwardNEAddress     IpAddress,
        ipeCfgAccessListForwardInIfIndex     INTEGER,
        ipeCfgAccessListForwardOutIfIndex    INTEGER,
        ipeCfgAccessListForwardSrcIpAddress  IpAddress,
        ipeCfgAccessListForwardSrcNetMask    IpAddress,
        ipeCfgAccessListForwardDstIpAddress  IpAddress,
        ipeCfgAccessListForwardDstNetMask    IpAddress,
        ipeCfgAccessListForwardProtocol      Integer32,
        ipeCfgAccessListForwardSrcPortNum    Integer32,
        ipeCfgAccessListForwardDstPortNum    Integer32,
        ipeCfgAccessListForwardAction        INTEGER,
        ipeCfgAccessListForwardRowStatus     RowStatus
    }

    ipeCfgAccessListForwardOrderNum OBJECT-TYPE
        SYNTAX       Integer32 (1..50)
        MAX-ACCESS   not-accessible
        STATUS       current
        DESCRIPTION  "Index of table(1-50)."
        ::= { ipeCfgAccessListForwardEntry 1 }

    ipeCfgAccessListForwardNEAddress OBJECT-TYPE
        SYNTAX       IpAddress
        MAX-ACCESS   not-accessible
        STATUS       current
        DESCRIPTION  "reserved."
        ::= { ipeCfgAccessListForwardEntry 2 }

    ipeCfgAccessListForwardInIfIndex OBJECT-TYPE
        SYNTAX       INTEGER {
                         any(0),
                         inband(3),
                         ne2(4),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  "IP Access Control Forward Filter Input"
        ::= { ipeCfgAccessListForwardEntry 3 }

    ipeCfgAccessListForwardOutIfIndex OBJECT-TYPE
        SYNTAX       INTEGER {
                         any(0),
                         inband(3),
                         ne2(4),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Forward Filter Output Interface.
            
            The value 'inband' is not supporte"
        ::= { ipeCfgAccessListForwardEntry 4 }

    ipeCfgAccessListForwardSrcIpAddress OBJECT-TYPE
        SYNTAX       IpAddress
        MAX-ACCESS   read-create
        STATUS       current
        DESCRIPTION  "IP Access Control Forward Filter Source IP Address."
        ::= { ipeCfgAccessListForwardEntry 5 }

    ipeCfgAccessListForwardSrcNetMask OBJECT-TYPE
        SYNTAX       IpAddress
        MAX-ACCESS   read-create
        STATUS       current
        DESCRIPTION  
            "IP Access Control Forward Filter Source Subnet Mask.
            '0.0.0.0' matches all IP addresses. i.e. '0.0.0.0' acts as 'Any'"
        ::= { ipeCfgAccessListForwardEntry 6 }

    ipeCfgAccessListForwardDstIpAddress OBJECT-TYPE
        SYNTAX       IpAddress
        MAX-ACCESS   read-create
        STATUS       current
        DESCRIPTION  
            "IP Access Control Forward Filter Destination IP Address."
        ::= { ipeCfgAccessListForwardEntry 7 }

    ipeCfgAccessListForwardDstNetMask OBJECT-TYPE
        SYNTAX       IpAddress
        MAX-ACCESS   read-create
        STATUS       current
        DESCRIPTION  
            "IP Access Control Forward Filter Destination Subnet Mask.
            '0.0.0.0' matches all IP addresses. i.e. '0.0.0.0' acts as
            'Any'."
        ::= { ipeCfgAccessListForwardEntry 8 }

    ipeCfgAccessListForwardProtocol OBJECT-TYPE
        SYNTAX       Integer32
        MAX-ACCESS   read-create
        STATUS       current
        DESCRIPTION  
            "IP Access Control Forward Filter Protocol.
            '-1' acts as 'Any'."
        ::= { ipeCfgAccessListForwardEntry 9 }

    ipeCfgAccessListForwardSrcPortNum OBJECT-TYPE
        SYNTAX       Integer32
        MAX-ACCESS   read-create
        STATUS       current
        DESCRIPTION  
            "IP Access Control Forward Filter Source Port Number.
            '-1' acts as 'Any'."
        ::= { ipeCfgAccessListForwardEntry 10 }

    ipeCfgAccessListForwardDstPortNum OBJECT-TYPE
        SYNTAX       Integer32
        MAX-ACCESS   read-create
        STATUS       current
        DESCRIPTION  
            "IP Access Control Forward Filter Destination Port Number.
            '-1' acts as 'Any'."
        ::= { ipeCfgAccessListForwardEntry 11 }

    ipeCfgAccessListForwardAction OBJECT-TYPE
        SYNTAX       INTEGER { permit(1), deny(2) }
        MAX-ACCESS   read-create
        STATUS       current
        DESCRIPTION  "IP Access Control Forward Filter Action."
        ::= { ipeCfgAccessListForwardEntry 12 }

    ipeCfgAccessListForwardRowStatus OBJECT-TYPE
        SYNTAX       RowStatus { active(1), createAndGo(4), destroy(6) }
        MAX-ACCESS   read-create
        STATUS       current
        DESCRIPTION  
            "This RowStatus has a status only 'active(1)'. 
            
            1) creating a entry
            When you make a new entry, you must SET objects indicated below.
            ipeCfgAccessListForwardAction
            ipeCfgAccessListForwardRowStatus <- createAndGo(4)
            
            
            When you are not setting a value of items as follows, it is set
            as 'any'.
            ipeCfgAccessListForwardInIfIndex
            ipeCfgAccessListForwardOutIfIndex
            ipeCfgAccessListForwardSrcIpAddress
            ipeCfgAccessListForwardSrcNetMask(*1)
            ipeCfgAccessListForwardDstIpAddress
            ipeCfgAccessListForwardDstNetMask(*2)
            ipeCfgAccessListForwardProtocol
            ipeCfgAccessListForwardSrcPortNum(*3)
            ipeCfgAccessListForwardDstPortNum(*3)
            
            *1 When you not set ipeCfgAccessListForwardSrcIpAddress, even
            when ipeCfgAccessListForwardSrcNetMask is set, it is set as
            'any'.When ipeCfgAccessListForwardSrcIpAddress set to 'any',
            ipeCfgAccessListForwardSrcNetMask is set as 'any'.
            *2 When you not set ipeCfgAccessListForwardDstIpAddress, even
            when ipeCfgAccessListForwardDstNetMask is set, it is set as
            'any'.When ipeCfgAccessListForwardDstIpAddress set to 'any',
            ipeCfgAccessListForwardDstNetMask is set as 'any'.
            *3 When you not set ipeCfgAccessListForwardProtocol to '6' or
            '17',, even when ipeCfgAccessListForwardSrcPortNum and
            ipeCfgAccessListForwardDstPortNum are set, it is set as 'any'.
            
            2) modifing a entry
            It isn't possible.
            
            3) deleting a entry
            When you SET a destroy(6) to ipeCfgAccessListForwardRowStatus,
            the entry is destroyed."
        ::= { ipeCfgAccessListForwardEntry 13 }

    ipeCfgAutoIpGroup OBJECT IDENTIFIER
        ::= { ipeConfigurationGroup 22 }

    ipeCfgAutoIpTable OBJECT-TYPE
        SYNTAX       SEQUENCE OF IpeCfgAutoIpEntry
        MAX-ACCESS   not-accessible
        STATUS       current
        DESCRIPTION  "Table of AutoIP configuration information."
        ::= { ipeCfgAutoIpGroup 1 }

    ipeCfgAutoIpEntry OBJECT-TYPE
        SYNTAX       IpeCfgAutoIpEntry
        MAX-ACCESS   not-accessible
        STATUS       current
        DESCRIPTION  "Entry of AutoIP configuration information."
        INDEX        { ipeCfgAutoIpIndex }
        ::= { ipeCfgAutoIpTable 1 }

    IpeCfgAutoIpEntry ::= SEQUENCE {
        ipeCfgAutoIpIndex           Integer32,
        ipeCfgAutoIpNEAddress       IpAddress,
        ipeCfgAutoIpNetworkAddress  IpAddress,
        ipeCfgAutoIpNetMask         IpAddress
    }

    ipeCfgAutoIpIndex OBJECT-TYPE
        SYNTAX       Integer32 (1..1)
        MAX-ACCESS   not-accessible
        STATUS       current
        DESCRIPTION  "Index of this table."
        ::= { ipeCfgAutoIpEntry 1 }

    ipeCfgAutoIpNEAddress OBJECT-TYPE
        SYNTAX       IpAddress
        MAX-ACCESS   not-accessible
        STATUS       current
        DESCRIPTION  "reserved."
        ::= { ipeCfgAutoIpEntry 2 }

    ipeCfgAutoIpNetworkAddress OBJECT-TYPE
        SYNTAX       IpAddress
        MAX-ACCESS   read-write
        STATUS       current
        DESCRIPTION  
            "Aggregation Net of AutoIP.
            A set value becomes a binary.
            Value range:0x00000000-0xdfffffff(0.0.0.0-223.255.255.255)
            If this value is changed in state of 'now setting' or 'automatic
            setting', AutoIP will set IP Address again."
        ::= { ipeCfgAutoIpEntry 3 }

    ipeCfgAutoIpNetMask OBJECT-TYPE
        SYNTAX       IpAddress
        MAX-ACCESS   read-write
        STATUS       current
        DESCRIPTION  
            "Aggregation NetMask of AutoIp.
            A set value becomes a binary.
            Value range:0x80000000-0xfffffffc(1-30bit)
            If this value is changed in state of 'now setting' or 'automatic
            setting', AutoIP will set IP Address again."
        ::= { ipeCfgAutoIpEntry 4 }

    ipeCfgSysNE1PortTable OBJECT-TYPE
        SYNTAX       SEQUENCE OF IpeCfgSysNE1PortEntry
        MAX-ACCESS   not-accessible
        STATUS       current
        DESCRIPTION  "NE1 Port Mode Configuration Table."
        ::= { ipeConfigurationGroup 25 }

    ipeCfgSysNE1PortEntry OBJECT-TYPE
        SYNTAX       IpeCfgSysNE1PortEntry
        MAX-ACCESS   not-accessible
        STATUS       current
        DESCRIPTION  ""
        INDEX        { ipeCfgSysNE1PortIndex }
        ::= { ipeCfgSysNE1PortTable 1 }

    IpeCfgSysNE1PortEntry ::= SEQUENCE {
        ipeCfgSysNE1PortIndex      Integer32,
        ipeCfgSysNE1PortNEAddress  IpAddress,
        ipeCfgSysNE1PortMode       INTEGER
    }

    ipeCfgSysNE1PortIndex OBJECT-TYPE
        SYNTAX       Integer32 (1..1)
        MAX-ACCESS   not-accessible
        STATUS       current
        DESCRIPTION  "Index of this table."
        ::= { ipeCfgSysNE1PortEntry 1 }

    ipeCfgSysNE1PortNEAddress OBJECT-TYPE
        SYNTAX       IpAddress
        MAX-ACCESS   not-accessible
        STATUS       current
        DESCRIPTION  "reserved."
        ::= { ipeCfgSysNE1PortEntry 2 }

    ipeCfgSysNE1PortMode OBJECT-TYPE
        SYNTAX       INTEGER { invalid(0), userPort(1), mgmtPort(2) }
        MAX-ACCESS   read-write
        STATUS       current
        DESCRIPTION  "NE1 Port Mode Configuration"
        DEFVAL       { userPort }
        ::= { ipeCfgSysNE1PortEntry 3 }

    ipeCfgRadiusGroup OBJECT IDENTIFIER
        ::= { ipeConfigurationGroup 27 }

    ipeCfgRadiusGeneralTable OBJECT-TYPE
        SYNTAX       SEQUENCE OF IpeCfgRadiusGeneralEntry
        MAX-ACCESS   not-accessible
        STATUS       current
        DESCRIPTION  "Configure RADIUS parameters."
        ::= { ipeCfgRadiusGroup 1 }

    ipeCfgRadiusGeneralEntry OBJECT-TYPE
        SYNTAX       IpeCfgRadiusGeneralEntry
        MAX-ACCESS   not-accessible
        STATUS       current
        DESCRIPTION  "..."
        INDEX        { ipeCfgRadiusGeneralIndex }
        ::= { ipeCfgRadiusGeneralTable 1 }

    IpeCfgRadiusGeneralEntry ::= SEQUENCE {
        ipeCfgRadiusGeneralIndex                 Integer32,
        ipeCfgRadiusGeneralNEAddress             IpAddress,
        ipeCfgRadiusGeneralAuthClientRetransmit  Integer32,
        ipeCfgRadiusGeneralAuthClientTimeout     Integer32
    }

    ipeCfgRadiusGeneralIndex OBJECT-TYPE
        SYNTAX       Integer32 (1..1)
        MAX-ACCESS   not-accessible
        STATUS       current
        DESCRIPTION  "Index of this table."
        ::= { ipeCfgRadiusGeneralEntry 1 }

    ipeCfgRadiusGeneralNEAddress OBJECT-TYPE
        SYNTAX       IpAddress
        MAX-ACCESS   not-accessible
        STATUS       current
        DESCRIPTION  "Reserved object for northbound interface."
        ::= { ipeCfgRadiusGeneralEntry 2 }

    ipeCfgRadiusGeneralAuthClientRetransmit OBJECT-TYPE
        SYNTAX       Integer32 (0..255)
        MAX-ACCESS   read-write
        STATUS       current
        DESCRIPTION  
            "Indicate maximum retransmit number of Access-Request
            message.
            The system retransmits Access-Request message to server
            according to this configuration."
        DEFVAL       { 3 }
        ::= { ipeCfgRadiusGeneralEntry 3 }

    ipeCfgRadiusGeneralAuthClientTimeout OBJECT-TYPE
        SYNTAX       Integer32 (0..65535)
        UNITS        "seconds"
        MAX-ACCESS   read-write
        STATUS       current
        DESCRIPTION  
            "Indicate timeout period for response to Access-Request
            message.
            In case response (Access-Accept message) is not received
            in this period, the system will retransmit message."
        DEFVAL       { 10 }
        ::= { ipeCfgRadiusGeneralEntry 4 }

    ipeCfgRadiusAuthServerExtTable OBJECT-TYPE
        SYNTAX       SEQUENCE OF IpeCfgRadiusAuthServerExtEntry
        MAX-ACCESS   not-accessible
        STATUS       current
        DESCRIPTION  "Configure RADIUS authentication server parameters."
        ::= { ipeCfgRadiusGroup 2 }

    ipeCfgRadiusAuthServerExtEntry OBJECT-TYPE
        SYNTAX       IpeCfgRadiusAuthServerExtEntry
        MAX-ACCESS   not-accessible
        STATUS       current
        DESCRIPTION  "..."
        INDEX        { ipeCfgRadiusAuthServerExtIndex }
        ::= { ipeCfgRadiusAuthServerExtTable 1 }

    IpeCfgRadiusAuthServerExtEntry ::= SEQUENCE {
        ipeCfgRadiusAuthServerExtIndex          Integer32,
        ipeCfgRadiusAuthServerNEAddress         IpAddress,
        ipeCfgRadiusAuthServerAddressType       INTEGER,
        ipeCfgRadiusAuthServerAddress           IpAddress,
        ipeCfgRadiusAuthClientServerPortNumber  Integer32,
        ipeCfgRadiusAuthClientPasswordType      INTEGER,
        ipeCfgRadiusAuthClientSecretKey         DisplayString,
        ipeCfgRadiusAuthServerExtRowStatus      RowStatus
    }

    ipeCfgRadiusAuthServerExtIndex OBJECT-TYPE
        SYNTAX       Integer32 (1..3)
        MAX-ACCESS   not-accessible
        STATUS       current
        DESCRIPTION  "Index of this table."
        ::= { ipeCfgRadiusAuthServerExtEntry 1 }

    ipeCfgRadiusAuthServerNEAddress OBJECT-TYPE
        SYNTAX       IpAddress
        MAX-ACCESS   not-accessible
        STATUS       current
        DESCRIPTION  "Reserved object for northbound interface."
        ::= { ipeCfgRadiusAuthServerExtEntry 2 }

    ipeCfgRadiusAuthServerAddressType OBJECT-TYPE
        SYNTAX       INTEGER { invalid(0), ipv4(1), ipv6(2) }
        MAX-ACCESS   read-create
        STATUS       current
        DESCRIPTION  
            "Indicate IP address type of this server.
            
            ipv4 : server has IPv4 address.
            ipv6 : server has IPv6 address. (NOT SUPPORTED)
            
            ipv6 will be supprted in future version."
        DEFVAL       { ipv4 }
        ::= { ipeCfgRadiusAuthServerExtEntry 3 }

    ipeCfgRadiusAuthServerAddress OBJECT-TYPE
        SYNTAX       IpAddress
        MAX-ACCESS   read-create
        STATUS       current
        DESCRIPTION  "Indicate IP address of this server."
        ::= { ipeCfgRadiusAuthServerExtEntry 4 }

    ipeCfgRadiusAuthClientServerPortNumber OBJECT-TYPE
        SYNTAX       Integer32 (0..65535)
        MAX-ACCESS   read-create
        STATUS       current
        DESCRIPTION  
            "Indicate port number of RADIUS authentication protocol on
            this server."
        DEFVAL       { 1812 }
        ::= { ipeCfgRadiusAuthServerExtEntry 5 }

    ipeCfgRadiusAuthClientPasswordType OBJECT-TYPE
        SYNTAX       INTEGER { invalid(0), user(1), chap(2) }
        MAX-ACCESS   read-create
        STATUS       current
        DESCRIPTION  
            "Indicate password authentication type. The system select
            password attribute on Access-Request message.
            
            user : use User-Password attribute.
            chap : use CHAP-Password attribute.
            
            See RFC 2865 for details."
        DEFVAL       { user }
        ::= { ipeCfgRadiusAuthServerExtEntry 6 }

    ipeCfgRadiusAuthClientSecretKey OBJECT-TYPE
        SYNTAX       DisplayString (SIZE(8..128))
        MAX-ACCESS   read-create
        STATUS       current
        DESCRIPTION  
            "Indicate RADIUS shared secret encrypted by blowfish.
            This object is used to confirm  received RADIUS message is
            sent from authenticated server.
            This object is also used to encrypt User-Password attribute
            on Access-Request message.
            See RFC 2865 for details.
            
            The secret key(before encryption) range is 1-63 characters.
            The characters which can be used are '-', '_','0'-'9', 
            'a'-'z' and 'A'-'Z'."
        ::= { ipeCfgRadiusAuthServerExtEntry 7 }

    ipeCfgRadiusAuthServerExtRowStatus OBJECT-TYPE
        SYNTAX       RowStatus
        MAX-ACCESS   read-create
        STATUS       current
        DESCRIPTION  "The row status of this table."
        ::= { ipeCfgRadiusAuthServerExtEntry 8 }

    ipeCfgRadiusPrivLevelGeneralTable OBJECT-TYPE
        SYNTAX       SEQUENCE OF IpeCfgRadiusPrivLevelGeneralEntry
        MAX-ACCESS   not-accessible
        STATUS       current
        DESCRIPTION  
            "Configure general privilege level for RADIUS
            authetication."
        ::= { ipeCfgRadiusGroup 3 }

    ipeCfgRadiusPrivLevelGeneralEntry OBJECT-TYPE
        SYNTAX       IpeCfgRadiusPrivLevelGeneralEntry
        MAX-ACCESS   not-accessible
        STATUS       current
        DESCRIPTION  "..."
        INDEX        { ipeCfgRadiusPrivLevelGeneralIndex }
        ::= { ipeCfgRadiusPrivLevelGeneralTable 1 }

    IpeCfgRadiusPrivLevelGeneralEntry ::= SEQUENCE {
        ipeCfgRadiusPrivLevelGeneralIndex          Integer32,
        ipeCfgRadiusPrivLevelGeneralNEAddress      IpAddress,
        ipeCfgRadiusPrivLevelGeneralDefaultAction  INTEGER,
        ipeCfgRadiusPrivLevelGeneralDefaultGroup   DisplayString
    }

    ipeCfgRadiusPrivLevelGeneralIndex OBJECT-TYPE
        SYNTAX       Integer32 (1..1)
        MAX-ACCESS   not-accessible
        STATUS       current
        DESCRIPTION  "Index of this table."
        ::= { ipeCfgRadiusPrivLevelGeneralEntry 1 }

    ipeCfgRadiusPrivLevelGeneralNEAddress OBJECT-TYPE
        SYNTAX       IpAddress
        MAX-ACCESS   not-accessible
        STATUS       current
        DESCRIPTION  "Reserved object for northbound interface."
        ::= { ipeCfgRadiusPrivLevelGeneralEntry 2 }

    ipeCfgRadiusPrivLevelGeneralDefaultAction OBJECT-TYPE
        SYNTAX       INTEGER { invalid(0), denyLogin(1), useDefaultGroup(2) }
        MAX-ACCESS   read-write
        STATUS       current
        DESCRIPTION  
            "Indicate system default action in case privilege level
            is not specified on Access-Accept message or received
            privilege level is set to disable in 
            ipeCfgRadiusGroupPrivLevelMappingEnable.
            
            denyLogin       : deny login.
            useDefaultGroup : use group specified in
                              ipeCfgRadiusPrivLevelGeneralDefaultGroup."
        DEFVAL       { useDefaultGroup }
        ::= { ipeCfgRadiusPrivLevelGeneralEntry 3 }

    ipeCfgRadiusPrivLevelGeneralDefaultGroup OBJECT-TYPE
        SYNTAX       DisplayString (SIZE(1..32))
        MAX-ACCESS   read-write
        STATUS       current
        DESCRIPTION  
            "Indicate default group in case privilege level is not
            specified.
            This object is effective only if
            ipeCfgRadiusPrivLevelGeneralDefaultAction is
            useDefaultGroup.
            
            The value of this object should be registered group name in
            the system (as ipeCfgAccountGroupName).
            
            The characters which can be used are '-', '_','0'-'9', 
            'a'-'z' and 'A'-'Z'."
        DEFVAL       { "Operator" }
        ::= { ipeCfgRadiusPrivLevelGeneralEntry 4 }

    ipeCfgRadiusGroupPrivLevelMappingTable OBJECT-TYPE
        SYNTAX       SEQUENCE OF IpeCfgRadiusGroupPrivLevelMappingEntry
        MAX-ACCESS   not-accessible
        STATUS       current
        DESCRIPTION  
            "Configure privilege level mapping for RADIUS
            authentication."
        ::= { ipeCfgRadiusGroup 4 }

    ipeCfgRadiusGroupPrivLevelMappingEntry OBJECT-TYPE
        SYNTAX       IpeCfgRadiusGroupPrivLevelMappingEntry
        MAX-ACCESS   not-accessible
        STATUS       current
        DESCRIPTION  "..."
        INDEX        { ipeCfgRadiusGroupPrivLevelMappingPrivLevel }
        ::= { ipeCfgRadiusGroupPrivLevelMappingTable 1 }

    IpeCfgRadiusGroupPrivLevelMappingEntry ::= SEQUENCE {
        ipeCfgRadiusGroupPrivLevelMappingPrivLevel  Integer32,
        ipeCfgRadiusGroupPrivLevelMappingNEAddress  IpAddress,
        ipeCfgRadiusGroupPrivLevelMappingEnable     INTEGER,
        ipeCfgRadiusGroupPrivLevelMappingGroup      DisplayString
    }

    ipeCfgRadiusGroupPrivLevelMappingPrivLevel OBJECT-TYPE
        SYNTAX       Integer32 (0..15)
        MAX-ACCESS   not-accessible
        STATUS       current
        DESCRIPTION  
            "The index of this table.
            The value corresponds to received privilege level on
            Access-Accept message."
        ::= { ipeCfgRadiusGroupPrivLevelMappingEntry 1 }

    ipeCfgRadiusGroupPrivLevelMappingNEAddress OBJECT-TYPE
        SYNTAX       IpAddress
        MAX-ACCESS   not-accessible
        STATUS       current
        DESCRIPTION  "Reserved object for northbound interface."
        ::= { ipeCfgRadiusGroupPrivLevelMappingEntry 2 }

    ipeCfgRadiusGroupPrivLevelMappingEnable OBJECT-TYPE
        SYNTAX       INTEGER { invalid(0), disable(1), enable(2) }
        MAX-ACCESS   read-write
        STATUS       current
        DESCRIPTION  
            "Enable or disable privilege level mapping on this
            privilege level.
            
            disable : privilege level mapping is disabled.
            enable  : privilege level mapping is enabled.
            
            The system default value of this object shown below.
            
            PrivLevel=1, 7, 15 : enable
            other PrivLevel    : disable
            
            In case this object is set to disable, the system
            behave according to 
            ipeCfgRadiusPrivLevelGeneralDefaultAction."
        DEFVAL       { disable }
        ::= { ipeCfgRadiusGroupPrivLevelMappingEntry 3 }

    ipeCfgRadiusGroupPrivLevelMappingGroup OBJECT-TYPE
        SYNTAX       DisplayString (SIZE(1..32))
        MAX-ACCESS   read-write
        STATUS       current
        DESCRIPTION  
            "Indicate group name correspond to privilege level.
            This object is effective only if 
            ipeCfgRadiusGroupPrivLevelMappingEnable is enable.
            When the system received Access-Accept message with certain
            privilege level, login user has same privilege as this
            group.
            
            The system default value of this object shown below.
            
            PrivLevel=1  : Operator
            PrivLevel=7  : Config
            PrivLevel=15 : Admin
            
            The value should be registered group name registerd in
            the system (as ipeCfgAccountGroupName).
            The characters which can be used are '-', '_','0'-'9', 
            'a'-'z' and 'A'-'Z'."
        ::= { ipeCfgRadiusGroupPrivLevelMappingEntry 4 }

    ipeCfgLldpGroup OBJECT IDENTIFIER
        ::= { ipeConfigurationGroup 28 }

    ipeCfgLldpTable OBJECT-TYPE
        SYNTAX       SEQUENCE OF IpeCfgLldpEntry
        MAX-ACCESS   not-accessible
        STATUS       current
        DESCRIPTION  "LLDP set up information table."
        ::= { ipeCfgLldpGroup 1 }

    ipeCfgLldpEntry OBJECT-TYPE
        SYNTAX       IpeCfgLldpEntry
        MAX-ACCESS   not-accessible
        STATUS       current
        DESCRIPTION  "entry of LLDP set up information table."
        INDEX        { ipeCfgLldpIndex }
        ::= { ipeCfgLldpTable 1 }

    IpeCfgLldpEntry ::= SEQUENCE {
        ipeCfgLldpIndex                      Integer32,
        ipeCfgLldpNEAddress                  IpAddress,
        ipeCfgLldpProprietaryModeMacAddress  MacAddress
    }

    ipeCfgLldpIndex OBJECT-TYPE
        SYNTAX       Integer32 (1..1)
        MAX-ACCESS   not-accessible
        STATUS       current
        DESCRIPTION  "Index of this table."
        ::= { ipeCfgLldpEntry 1 }

    ipeCfgLldpNEAddress OBJECT-TYPE
        SYNTAX       IpAddress
        MAX-ACCESS   not-accessible
        STATUS       current
        DESCRIPTION  "reserved."
        ::= { ipeCfgLldpEntry 2 }

    ipeCfgLldpProprietaryModeMacAddress OBJECT-TYPE
        SYNTAX       MacAddress
        MAX-ACCESS   read-write
        STATUS       current
        DESCRIPTION  
            "MAC address of LLDP Frame in NEC mode.
            This object is effective only if ipeCfgPortXXXXXLldpMode is set
            to proprietaryMode."
        DEFVAL       { '01004c01da50'h }
        ::= { ipeCfgLldpEntry 3 }

    ipeCommunicationsGroup OBJECT IDENTIFIER
        ::= { system5 4 }

    ipeNeighborInfoTable OBJECT-TYPE
        SYNTAX       SEQUENCE OF IpeNeighborInfoEntry
        MAX-ACCESS   not-accessible
        STATUS       current
        DESCRIPTION  "Neighbor NE table."
        ::= { ipeCommunicationsGroup 1 }

    ipeNeighborInfoEntry OBJECT-TYPE
        SYNTAX       IpeNeighborInfoEntry
        MAX-ACCESS   not-accessible
        STATUS       current
        DESCRIPTION  "Neighbor NE entry."
        INDEX        { ipeNeighborInfoIndex }
        ::= { ipeNeighborInfoTable 1 }

    IpeNeighborInfoEntry ::= SEQUENCE {
        ipeNeighborInfoIndex      InterfaceIndex,
        ipeNeighborInfoNEAddress  IpAddress,
        ipeNeighborIpAddress      OCTET STRING
    }

    ipeNeighborInfoIndex OBJECT-TYPE
        SYNTAX       InterfaceIndex
        MAX-ACCESS   not-accessible
        STATUS       current
        DESCRIPTION  "Index of this table."
        ::= { ipeNeighborInfoEntry 1 }

    ipeNeighborInfoNEAddress OBJECT-TYPE
        SYNTAX       IpAddress
        MAX-ACCESS   not-accessible
        STATUS       current
        DESCRIPTION  "reserved."
        ::= { ipeNeighborInfoEntry 2 }

    ipeNeighborIpAddress OBJECT-TYPE
        SYNTAX       OCTET STRING (SIZE(0..240))
        MAX-ACCESS   read-only
        STATUS       current
        DESCRIPTION  
            "[iPASOLINK200/400/1000series/EX/iX]
            Neighbor NE is displayed as unit of registration every eight
            bytes of Internet Protocol address (4byte) + Node TYPE(4byte).The
            number of maximum registration is 30 (240byte). attention: ne2
            set the IpAddress only, do not set the Node type.
            
            [iPASOLINK VR series]
            The number of maximum registration is 13.
            Type(1byte) and Length(1byte) are common information is 2byte.
            
            Unit of registration of each neighbor as 
            IPv4 Address(4bytes) + Node Type(4bytes) + MAC Address(6bytes) +
            ifindex(4bytes)."
        ::= { ipeNeighborInfoEntry 3 }

    ipeStatusGroup OBJECT IDENTIFIER
        ::= { system5 6 }

    ipeStsNtp OBJECT IDENTIFIER
        ::= { ipeStatusGroup 1 }

    ipeStsNtpStatisticsTable OBJECT-TYPE
        SYNTAX       SEQUENCE OF IpeStsNtpStatisticsEntry
        MAX-ACCESS   not-accessible
        STATUS       current
        DESCRIPTION  "Table of NTP statistics."
        ::= { ipeStsNtp 1 }

    ipeStsNtpStatisticsEntry OBJECT-TYPE
        SYNTAX       IpeStsNtpStatisticsEntry
        MAX-ACCESS   not-accessible
        STATUS       current
        DESCRIPTION  "Entry of NTP statistics."
        INDEX        { ipeStsNtpStatisticsIndex }
        ::= { ipeStsNtpStatisticsTable 1 }

    IpeStsNtpStatisticsEntry ::= SEQUENCE {
        ipeStsNtpStatisticsIndex      Integer32,
        ipeStsNtpStatisticsNEAddress  IpAddress,
        ipeStsNtpSyncStatusInfo       OCTET STRING,
        ipeStsNtpSetTime              INTEGER
    }

    ipeStsNtpStatisticsIndex OBJECT-TYPE
        SYNTAX       Integer32 (1..1)
        MAX-ACCESS   not-accessible
        STATUS       current
        DESCRIPTION  "Index of this table."
        ::= { ipeStsNtpStatisticsEntry 1 }

    ipeStsNtpStatisticsNEAddress OBJECT-TYPE
        SYNTAX       IpAddress
        MAX-ACCESS   not-accessible
        STATUS       current
        DESCRIPTION  "reserved."
        ::= { ipeStsNtpStatisticsEntry 2 }

    ipeStsNtpSyncStatusInfo OBJECT-TYPE
        SYNTAX       OCTET STRING (SIZE(1..1024))
        MAX-ACCESS   read-only
        STATUS       current
        DESCRIPTION  "Synchronous state information."
        ::= { ipeStsNtpStatisticsEntry 3 }

    ipeStsNtpSetTime OBJECT-TYPE
        SYNTAX       INTEGER { notSetManually(0), setManually(1) }
        MAX-ACCESS   read-only
        STATUS       current
        DESCRIPTION  "Presence of time manual setting."
        ::= { ipeStsNtpStatisticsEntry 4 }

    ipeStsFtp OBJECT IDENTIFIER
        ::= { ipeStatusGroup 2 }

    ipeStsFtpStatusTable OBJECT-TYPE
        SYNTAX       SEQUENCE OF IpeStsFtpStatusEntry
        MAX-ACCESS   not-accessible
        STATUS       current
        DESCRIPTION  "Table of FTP status."
        ::= { ipeStsFtp 1 }

    ipeStsFtpStatusEntry OBJECT-TYPE
        SYNTAX       IpeStsFtpStatusEntry
        MAX-ACCESS   not-accessible
        STATUS       current
        DESCRIPTION  "Entry of FTP status."
        INDEX        { ipeStsFtpStatusIndex }
        ::= { ipeStsFtpStatusTable 1 }

    IpeStsFtpStatusEntry ::= SEQUENCE {
        ipeStsFtpStatusIndex           Integer32,
        ipeStsFtpStatusNEAddress       IpAddress,
        ipeStsFtpStatusLoginUser       DisplayString,
        ipeStsFtpStatusLoginIpAddress  IpAddress,
        ipeStsFtpStatusSessionId       Integer32
    }

    ipeStsFtpStatusIndex OBJECT-TYPE
        SYNTAX       Integer32 (1..3)
        MAX-ACCESS   not-accessible
        STATUS       current
        DESCRIPTION  "Index of this table."
        ::= { ipeStsFtpStatusEntry 1 }

    ipeStsFtpStatusNEAddress OBJECT-TYPE
        SYNTAX       IpAddress
        MAX-ACCESS   not-accessible
        STATUS       current
        DESCRIPTION  "reserved."
        ::= { ipeStsFtpStatusEntry 2 }

    ipeStsFtpStatusLoginUser OBJECT-TYPE
        SYNTAX       DisplayString (SIZE(1..31))
        MAX-ACCESS   read-only
        STATUS       current
        DESCRIPTION  "Name of Connected user."
        ::= { ipeStsFtpStatusEntry 3 }

    ipeStsFtpStatusLoginIpAddress OBJECT-TYPE
        SYNTAX       IpAddress
        MAX-ACCESS   read-only
        STATUS       current
        DESCRIPTION  "IP Address of Connected user ."
        ::= { ipeStsFtpStatusEntry 4 }

    ipeStsFtpStatusSessionId OBJECT-TYPE
        SYNTAX       Integer32
        MAX-ACCESS   read-only
        STATUS       current
        DESCRIPTION  "Session information of Connected User."
        ::= { ipeStsFtpStatusEntry 5 }

    ipeStsSftp OBJECT IDENTIFIER
        ::= { ipeStatusGroup 3 }

    ipeStsSftpStatusTable OBJECT-TYPE
        SYNTAX       SEQUENCE OF IpeStsSftpStatusEntry
        MAX-ACCESS   not-accessible
        STATUS       current
        DESCRIPTION  "Table of SFTP status ."
        ::= { ipeStsSftp 1 }

    ipeStsSftpStatusEntry OBJECT-TYPE
        SYNTAX       IpeStsSftpStatusEntry
        MAX-ACCESS   not-accessible
        STATUS       current
        DESCRIPTION  "Entry of SFTP status ."
        INDEX        { ipeStsSftpStatusIndex }
        ::= { ipeStsSftpStatusTable 1 }

    IpeStsSftpStatusEntry ::= SEQUENCE {
        ipeStsSftpStatusIndex           Integer32,
        ipeStsSftpStatusNEAddress       IpAddress,
        ipeStsSftpStatusLoginUser       DisplayString,
        ipeStsSftpStatusLoginIpAddress  IpAddress,
        ipeStsSftpStatusSessionId       Integer32
    }

    ipeStsSftpStatusIndex OBJECT-TYPE
        SYNTAX       Integer32 (1..3)
        MAX-ACCESS   not-accessible
        STATUS       current
        DESCRIPTION  "Index of this table."
        ::= { ipeStsSftpStatusEntry 1 }

    ipeStsSftpStatusNEAddress OBJECT-TYPE
        SYNTAX       IpAddress
        MAX-ACCESS   not-accessible
        STATUS       current
        DESCRIPTION  "reserved."
        ::= { ipeStsSftpStatusEntry 2 }

    ipeStsSftpStatusLoginUser OBJECT-TYPE
        SYNTAX       DisplayString (SIZE(1..31))
        MAX-ACCESS   read-only
        STATUS       current
        DESCRIPTION  "Name of Connected user."
        ::= { ipeStsSftpStatusEntry 3 }

    ipeStsSftpStatusLoginIpAddress OBJECT-TYPE
        SYNTAX       IpAddress
        MAX-ACCESS   read-only
        STATUS       current
        DESCRIPTION  "IP Address of Connected user ."
        ::= { ipeStsSftpStatusEntry 4 }

    ipeStsSftpStatusSessionId OBJECT-TYPE
        SYNTAX       Integer32
        MAX-ACCESS   read-only
        STATUS       current
        DESCRIPTION  "Session information of Connected User."
        ::= { ipeStsSftpStatusEntry 5 }

    ipeStsHttp OBJECT IDENTIFIER
        ::= { ipeStatusGroup 4 }

    ipeStsHttpStatusTable OBJECT-TYPE
        SYNTAX       SEQUENCE OF IpeStsHttpStatusEntry
        MAX-ACCESS   not-accessible
        STATUS       current
        DESCRIPTION  "Table of HTTP status."
        ::= { ipeStsHttp 1 }

    ipeStsHttpStatusEntry OBJECT-TYPE
        SYNTAX       IpeStsHttpStatusEntry
        MAX-ACCESS   not-accessible
        STATUS       current
        DESCRIPTION  "Entry of HTTP status."
        INDEX        { ipeStsHttpStatusIndex }
        ::= { ipeStsHttpStatusTable 1 }

    IpeStsHttpStatusEntry ::= SEQUENCE {
        ipeStsHttpStatusIndex           Integer32,
        ipeStsHttpStatusNEAddress       IpAddress,
        ipeStsHttpStatusLoginUser       DisplayString,
        ipeStsHttpStatusLoginIpAddress  IpAddress,
        ipeStsHttpStatusSessionId       Integer32
    }

    ipeStsHttpStatusIndex OBJECT-TYPE
        SYNTAX       Integer32 (1..5)
        MAX-ACCESS   not-accessible
        STATUS       current
        DESCRIPTION  "Index of this table."
        ::= { ipeStsHttpStatusEntry 1 }

    ipeStsHttpStatusNEAddress OBJECT-TYPE
        SYNTAX       IpAddress
        MAX-ACCESS   not-accessible
        STATUS       current
        DESCRIPTION  "reserved."
        ::= { ipeStsHttpStatusEntry 2 }

    ipeStsHttpStatusLoginUser OBJECT-TYPE
        SYNTAX       DisplayString (SIZE(1..31))
        MAX-ACCESS   read-only
        STATUS       current
        DESCRIPTION  "Name of Connected user."
        ::= { ipeStsHttpStatusEntry 3 }

    ipeStsHttpStatusLoginIpAddress OBJECT-TYPE
        SYNTAX       IpAddress
        MAX-ACCESS   read-only
        STATUS       current
        DESCRIPTION  "IP Address of Connected user ."
        ::= { ipeStsHttpStatusEntry 4 }

    ipeStsHttpStatusSessionId OBJECT-TYPE
        SYNTAX       Integer32
        MAX-ACCESS   read-only
        STATUS       current
        DESCRIPTION  "Session information of Connected User."
        ::= { ipeStsHttpStatusEntry 5 }

    ipeStsHttps OBJECT IDENTIFIER
        ::= { ipeStatusGroup 5 }

    ipeStsHttpsStatusTable OBJECT-TYPE
        SYNTAX       SEQUENCE OF IpeStsHttpsStatusEntry
        MAX-ACCESS   not-accessible
        STATUS       current
        DESCRIPTION  "Table of HTTPS status."
        ::= { ipeStsHttps 1 }

    ipeStsHttpsStatusEntry OBJECT-TYPE
        SYNTAX       IpeStsHttpsStatusEntry
        MAX-ACCESS   not-accessible
        STATUS       current
        DESCRIPTION  "Entry of HTTPS status."
        INDEX        { ipeStsHttpsStatusIndex }
        ::= { ipeStsHttpsStatusTable 1 }

    IpeStsHttpsStatusEntry ::= SEQUENCE {
        ipeStsHttpsStatusIndex           Integer32,
        ipeStsHttpsStatusNEAddress       IpAddress,
        ipeStsHttpsStatusLoginUser       DisplayString,
        ipeStsHttpsStatusLoginIpAddress  IpAddress,
        ipeStsHttpsStatusSessionId       Integer32
    }

    ipeStsHttpsStatusIndex OBJECT-TYPE
        SYNTAX       Integer32 (1..5)
        MAX-ACCESS   not-accessible
        STATUS       current
        DESCRIPTION  "Index of this table."
        ::= { ipeStsHttpsStatusEntry 1 }

    ipeStsHttpsStatusNEAddress OBJECT-TYPE
        SYNTAX       IpAddress
        MAX-ACCESS   not-accessible
        STATUS       current
        DESCRIPTION  "reserved."
        ::= { ipeStsHttpsStatusEntry 2 }

    ipeStsHttpsStatusLoginUser OBJECT-TYPE
        SYNTAX       DisplayString (SIZE(1..31))
        MAX-ACCESS   read-only
        STATUS       current
        DESCRIPTION  "Name of Connected user."
        ::= { ipeStsHttpsStatusEntry 3 }

    ipeStsHttpsStatusLoginIpAddress OBJECT-TYPE
        SYNTAX       IpAddress
        MAX-ACCESS   read-only
        STATUS       current
        DESCRIPTION  "IP Address of Connected user."
        ::= { ipeStsHttpsStatusEntry 4 }

    ipeStsHttpsStatusSessionId OBJECT-TYPE
        SYNTAX       Integer32
        MAX-ACCESS   read-only
        STATUS       current
        DESCRIPTION  "Session information of Connected User."
        ::= { ipeStsHttpsStatusEntry 5 }

    ipeStsStp OBJECT IDENTIFIER
        ::= { ipeStatusGroup 6 }

    ipeStsStpBridgeTable OBJECT-TYPE
        SYNTAX       SEQUENCE OF IpeStsStpBridgeEntry
        MAX-ACCESS   not-accessible
        STATUS       current
        DESCRIPTION  "Table of STP status."
        ::= { ipeStsStp 1 }

    ipeStsStpBridgeEntry OBJECT-TYPE
        SYNTAX       IpeStsStpBridgeEntry
        MAX-ACCESS   not-accessible
        STATUS       current
        DESCRIPTION  "entry of  STP status."
        INDEX        { ipeStsStpBridgeIndex }
        ::= { ipeStsStpBridgeTable 1 }

    IpeStsStpBridgeEntry ::= SEQUENCE {
        ipeStsStpBridgeIndex                  Integer32,
        ipeStsStpBridgeNEAddress              IpAddress,
        ipeStsStpBridgeProtocolSpecification  INTEGER,
        ipeStsStpBridgeDesignatedRoot         BridgeId,
        ipeStsStpBridgeRootCost               Integer32,
        ipeStsStpBridgeRootPort               Integer32,
        ipeStsStpBridgeMaxAge                 Timeout,
        ipeStsStpBridgeHelloTime              Timeout,
        ipeStsStpBridgeForwardDelay           Timeout
    }

    ipeStsStpBridgeIndex OBJECT-TYPE
        SYNTAX       Integer32 (1..20)
        MAX-ACCESS   not-accessible
        STATUS       current
        DESCRIPTION  "Index of this table."
        ::= { ipeStsStpBridgeEntry 1 }

    ipeStsStpBridgeNEAddress OBJECT-TYPE
        SYNTAX       IpAddress
        MAX-ACCESS   not-accessible
        STATUS       current
        DESCRIPTION  "reserved."
        ::= { ipeStsStpBridgeEntry 2 }

    ipeStsStpBridgeProtocolSpecification OBJECT-TYPE
        SYNTAX       INTEGER { unknown(1), decLb100(2), ieee8021d(3) }
        MAX-ACCESS   read-only
        STATUS       current
        DESCRIPTION  
            "An indication of what version of the Spanning Tree Protocol is
            being run.  The value 'decLb100(2)' indicates the DEC LANbridge
            100 Spanning Tree protocol.  IEEE 802.1d implementations will
            return 'ieee8021d(3)'.  If future versions of the IEEE Spanning
            Tree Protocol are released that are incompatible with the current
            version a new value will be defined.
            It's a fixed Ieee8021d(3)."
        ::= { ipeStsStpBridgeEntry 3 }

    ipeStsStpBridgeDesignatedRoot OBJECT-TYPE
        SYNTAX       BridgeId
        MAX-ACCESS   read-only
        STATUS       current
        DESCRIPTION  
            "The bridge identifier of the root of the spanning tree as
            determined by the Spanning Tree Protocol as executed by this
            node.  This value is used as the Root Identifier parameter in all
            Configuration Bridge PDUs originated by this node."
        ::= { ipeStsStpBridgeEntry 4 }

    ipeStsStpBridgeRootCost OBJECT-TYPE
        SYNTAX       Integer32
        MAX-ACCESS   read-only
        STATUS       current
        DESCRIPTION  
            "The cost of the path to the root as seen from this bridge."
        ::= { ipeStsStpBridgeEntry 5 }

    ipeStsStpBridgeRootPort OBJECT-TYPE
        SYNTAX       Integer32
        MAX-ACCESS   read-only
        STATUS       current
        DESCRIPTION  
            "The port number of the port which offers the lowest cost path
            from this bridge to the root bridge."
        ::= { ipeStsStpBridgeEntry 6 }

    ipeStsStpBridgeMaxAge OBJECT-TYPE
        SYNTAX       Timeout
        MAX-ACCESS   read-only
        STATUS       current
        DESCRIPTION  
            "The maximum age of Spanning Tree Protocol information learned
            from the network on any port before it is discarded, in units of
            hundredths of
            a second. This is the actual value that this bridge is currently
            using."
        ::= { ipeStsStpBridgeEntry 7 }

    ipeStsStpBridgeHelloTime OBJECT-TYPE
        SYNTAX       Timeout
        MAX-ACCESS   read-only
        STATUS       current
        DESCRIPTION  
            "The amount of time between the transmission of Configuration
            bridge PDUs by this node on any port when it is the root of the
            spanning tree or trying to become so, in units of hundredths of a
            second. This is the actual value that this bridge is currently
            using."
        ::= { ipeStsStpBridgeEntry 8 }

    ipeStsStpBridgeForwardDelay OBJECT-TYPE
        SYNTAX       Timeout
        MAX-ACCESS   read-only
        STATUS       current
        DESCRIPTION  
            "This time value, measured in units of hundredths of a second,
            controls how fast a port changes its spanning state when moving
            towards the Forwarding state.  The value determines how long the
            port stays in each of the Listening and Learning states, which
            precede the Forwarding state.  This value is also used, when a
            topology change has been detected and is underway, to age all
            dynamic entries in the Forwarding Database."
        ::= { ipeStsStpBridgeEntry 9 }

    ipeStsStpPortTable OBJECT-TYPE
        SYNTAX       SEQUENCE OF IpeStsStpPortEntry
        MAX-ACCESS   not-accessible
        STATUS       current
        DESCRIPTION  
            "table of STP port status.
            When the system is running on the mplsTp mode, this table may
            return wrong value. (must not use this table on mplsTp mode)."
        ::= { ipeStsStp 2 }

    ipeStsStpPortEntry OBJECT-TYPE
        SYNTAX       IpeStsStpPortEntry
        MAX-ACCESS   not-accessible
        STATUS       current
        DESCRIPTION  "entry of  STP port status table."
        INDEX        { ipeStsStpPortIfIndex, ipeStsStpPortBridgeIndex }
        ::= { ipeStsStpPortTable 1 }

    IpeStsStpPortEntry ::= SEQUENCE {
        ipeStsStpPortIfIndex           InterfaceIndex,
        ipeStsStpPortBridgeIndex       Integer32,
        ipeStsStpPortNEAddress         IpAddress,
        ipeStsStpPortPortState         INTEGER,
        ipeStsStpPortDesignatedRoot    BridgeId,
        ipeStsStpPortDesignatedCost    Integer32,
        ipeStsStpPortDesignatedBridge  BridgeId,
        ipeStsStpPortDesignatedPort    OCTET STRING
    }

    ipeStsStpPortIfIndex OBJECT-TYPE
        SYNTAX       InterfaceIndex
        MAX-ACCESS   not-accessible
        STATUS       current
        DESCRIPTION  "Index of this table."
        ::= { ipeStsStpPortEntry 1 }

    ipeStsStpPortBridgeIndex OBJECT-TYPE
        SYNTAX       Integer32 (1..20)
        MAX-ACCESS   not-accessible
        STATUS       current
        DESCRIPTION  "Index of this table."
        ::= { ipeStsStpPortEntry 2 }

    ipeStsStpPortNEAddress OBJECT-TYPE
        SYNTAX       IpAddress
        MAX-ACCESS   not-accessible
        STATUS       current
        DESCRIPTION  "reserved."
        ::= { ipeStsStpPortEntry 3 }

    ipeStsStpPortPortState OBJECT-TYPE
        SYNTAX       INTEGER {
                         disabled(1),
                         blocking(2),
                         listening(3),
                         learning(4),
                         forwarding(5),
                         broken(6)
                     }
        MAX-ACCESS   read-only
        STATUS       current
        DESCRIPTION  
            "The port's current state as defined by application of the
            Spanning Tree Protocol."
        ::= { ipeStsStpPortEntry 4 }

    ipeStsStpPortDesignatedRoot OBJECT-TYPE
        SYNTAX       BridgeId
        MAX-ACCESS   read-only
        STATUS       current
        DESCRIPTION  
            "The unique Bridge Identifier of the Bridge recorded as the Root
            in the Configuration BPDUs transmitted by the Designated Bridge
            for the  segment to which the port is attached."
        ::= { ipeStsStpPortEntry 5 }

    ipeStsStpPortDesignatedCost OBJECT-TYPE
        SYNTAX       Integer32
        MAX-ACCESS   read-only
        STATUS       current
        DESCRIPTION  
            "The path cost of the Designated Port of the segment connected to
            this port.  This value is compared to the Root Path Cost field in
            received bridge PDUs."
        ::= { ipeStsStpPortEntry 6 }

    ipeStsStpPortDesignatedBridge OBJECT-TYPE
        SYNTAX       BridgeId
        MAX-ACCESS   read-only
        STATUS       current
        DESCRIPTION  
            "The Bridge Identifier of the bridge which this port considers to
            be the Designated Bridge for this port's segment."
        ::= { ipeStsStpPortEntry 7 }

    ipeStsStpPortDesignatedPort OBJECT-TYPE
        SYNTAX       OCTET STRING (SIZE(2..2))
        MAX-ACCESS   read-only
        STATUS       current
        DESCRIPTION  
            "The Port Identifier of the port on the Designated Bridge for
            this port's segment."
        ::= { ipeStsStpPortEntry 8 }

    ipeStsPort OBJECT IDENTIFIER
        ::= { ipeStatusGroup 7 }

    ipeStsPortEtherTable OBJECT-TYPE
        SYNTAX       SEQUENCE OF IpeStsPortEtherEntry
        MAX-ACCESS   not-accessible
        STATUS       current
        DESCRIPTION  "Table of port status."
        ::= { ipeStsPort 1 }

    ipeStsPortEtherEntry OBJECT-TYPE
        SYNTAX       IpeStsPortEtherEntry
        MAX-ACCESS   not-accessible
        STATUS       current
        DESCRIPTION  "entry of  port status table."
        INDEX        { ipeStsPortEtherIfIndex }
        ::= { ipeStsPortEtherTable 1 }

    IpeStsPortEtherEntry ::= SEQUENCE {
        ipeStsPortEtherIfIndex      InterfaceIndex,
        ipeStsPortEtherNEAddress    IpAddress,
        ipeStsPortEtherLinkUp       Integer32,
        ipeStsPortEtherSpeed        Integer32,
        ipeStsPortEtherDuplex       Integer32,
        ipeStsPortEtherFlowControl  Integer32
    }

    ipeStsPortEtherIfIndex OBJECT-TYPE
        SYNTAX       InterfaceIndex
        MAX-ACCESS   not-accessible
        STATUS       current
        DESCRIPTION  "Index of this table."
        ::= { ipeStsPortEtherEntry 1 }

    ipeStsPortEtherNEAddress OBJECT-TYPE
        SYNTAX       IpAddress
        MAX-ACCESS   not-accessible
        STATUS       current
        DESCRIPTION  "reserved."
        ::= { ipeStsPortEtherEntry 2 }

    ipeStsPortEtherLinkUp OBJECT-TYPE
        SYNTAX       Integer32
        MAX-ACCESS   read-only
        STATUS       current
        DESCRIPTION  
            "Link Up/Down of I/F.
            value range:1 LinkUp
                        2 LinkDown"
        ::= { ipeStsPortEtherEntry 3 }

    ipeStsPortEtherSpeed OBJECT-TYPE
        SYNTAX       Integer32
        MAX-ACCESS   read-only
        STATUS       current
        DESCRIPTION  
            "SpeedI of I/F.
            value range:10   10Mb/s
                        100  100Mb/s
                        1000 1000Mb/s"
        ::= { ipeStsPortEtherEntry 4 }

    ipeStsPortEtherDuplex OBJECT-TYPE
        SYNTAX       Integer32
        MAX-ACCESS   read-only
        STATUS       current
        DESCRIPTION  
            "Duplex of I/F.
            value range:1 half duplex
                        2 full duplex"
        ::= { ipeStsPortEtherEntry 5 }

    ipeStsPortEtherFlowControl OBJECT-TYPE
        SYNTAX       Integer32
        MAX-ACCESS   read-only
        STATUS       current
        DESCRIPTION  
            "FlowControl of I/F.
            value range:0 flowctl none
                        1  receive only
                        2  transfer only
                        3  receive and transfer"
        ::= { ipeStsPortEtherEntry 6 }

    ipeStsPortNe2Table OBJECT-TYPE
        SYNTAX       SEQUENCE OF IpeStsPortNe2Entry
        MAX-ACCESS   not-accessible
        STATUS       current
        DESCRIPTION  "Table of NE2 port status table."
        ::= { ipeStsPort 2 }

    ipeStsPortNe2Entry OBJECT-TYPE
        SYNTAX       IpeStsPortNe2Entry
        MAX-ACCESS   not-accessible
        STATUS       current
        DESCRIPTION  "entry of NE2 port status entry."
        INDEX        { ipeStsPortNe2IfIndex }
        ::= { ipeStsPortNe2Table 1 }

    IpeStsPortNe2Entry ::= SEQUENCE {
        ipeStsPortNe2IfIndex    InterfaceIndex,
        ipeStsPortNe2NEAddress  IpAddress,
        ipeStsPortNe2LinkUp     Integer32
    }

    ipeStsPortNe2IfIndex OBJECT-TYPE
        SYNTAX       InterfaceIndex
        MAX-ACCESS   not-accessible
        STATUS       current
        DESCRIPTION  "Index of this table."
        ::= { ipeStsPortNe2Entry 1 }

    ipeStsPortNe2NEAddress OBJECT-TYPE
        SYNTAX       IpAddress
        MAX-ACCESS   not-accessible
        STATUS       current
        DESCRIPTION  "reserved."
        ::= { ipeStsPortNe2Entry 2 }

    ipeStsPortNe2LinkUp OBJECT-TYPE
        SYNTAX       Integer32
        MAX-ACCESS   read-only
        STATUS       current
        DESCRIPTION  "Link Up/Down of I/F."
        ::= { ipeStsPortNe2Entry 3 }

    ipeStsBridge OBJECT IDENTIFIER
        ::= { ipeStatusGroup 8 }

    ipeStsBridgeFdbTable OBJECT-TYPE
        SYNTAX       SEQUENCE OF IpeStsBridgeFdbEntry
        MAX-ACCESS   not-accessible
        STATUS       obsolete
        DESCRIPTION  "Learning MAC table of bridge."
        ::= { ipeStsBridge 1 }

    ipeStsBridgeFdbEntry OBJECT-TYPE
        SYNTAX       IpeStsBridgeFdbEntry
        MAX-ACCESS   not-accessible
        STATUS       obsolete
        DESCRIPTION  "Learning MAC table entry of bridge."
        INDEX        {
                         ipeStsBridgeFdbBridgeIndex,
                         ipeStsBridgeFdbIfIndex,
                         ipeStsBridgeFdbIndex
                     }
        ::= { ipeStsBridgeFdbTable 1 }

    IpeStsBridgeFdbEntry ::= SEQUENCE {
        ipeStsBridgeFdbBridgeIndex  Integer32,
        ipeStsBridgeFdbIfIndex      InterfaceIndex,
        ipeStsBridgeFdbIndex        Integer32,
        ipeStsBridgeFdbNEAddress    IpAddress,
        ipeStsBridgeFdbAddress      MacAddress
    }

    ipeStsBridgeFdbBridgeIndex OBJECT-TYPE
        SYNTAX       Integer32 (1..20)
        MAX-ACCESS   not-accessible
        STATUS       obsolete
        DESCRIPTION  "Index of this table."
        ::= { ipeStsBridgeFdbEntry 1 }

    ipeStsBridgeFdbIfIndex OBJECT-TYPE
        SYNTAX       InterfaceIndex
        MAX-ACCESS   not-accessible
        STATUS       obsolete
        DESCRIPTION  "Index of this table."
        ::= { ipeStsBridgeFdbEntry 2 }

    ipeStsBridgeFdbIndex OBJECT-TYPE
        SYNTAX       Integer32 (1..63)
        MAX-ACCESS   not-accessible
        STATUS       obsolete
        DESCRIPTION  "Index of this table."
        ::= { ipeStsBridgeFdbEntry 3 }

    ipeStsBridgeFdbNEAddress OBJECT-TYPE
        SYNTAX       IpAddress
        MAX-ACCESS   not-accessible
        STATUS       obsolete
        DESCRIPTION  "reserved."
        ::= { ipeStsBridgeFdbEntry 4 }

    ipeStsBridgeFdbAddress OBJECT-TYPE
        SYNTAX       MacAddress
        MAX-ACCESS   read-only
        STATUS       obsolete
        DESCRIPTION  
            "Learning MAC address of bridge.
            When Snmpwalk is done, it becomes operation like ReadCreate."
        ::= { ipeStsBridgeFdbEntry 5 }

    ipeStsAutoIp OBJECT IDENTIFIER
        ::= { ipeStatusGroup 9 }

    ipeStsAutoIpTable OBJECT-TYPE
        SYNTAX       SEQUENCE OF IpeStsAutoIpEntry
        MAX-ACCESS   not-accessible
        STATUS       current
        DESCRIPTION  "Table of AutoIP status."
        ::= { ipeStsAutoIp 1 }

    ipeStsAutoIpEntry OBJECT-TYPE
        SYNTAX       IpeStsAutoIpEntry
        MAX-ACCESS   not-accessible
        STATUS       current
        DESCRIPTION  "entry of AutoIP status table."
        INDEX        { ipeStsAutoIpIndex }
        ::= { ipeStsAutoIpTable 1 }

    IpeStsAutoIpEntry ::= SEQUENCE {
        ipeStsAutoIpIndex        Integer32,
        ipeStsAutoIpNEAddress    IpAddress,
        ipeStsAutoIpState        Integer32,
        ipeStsAutoIpTempAddress  IpAddress
    }

    ipeStsAutoIpIndex OBJECT-TYPE
        SYNTAX       Integer32 (1..1)
        MAX-ACCESS   not-accessible
        STATUS       current
        DESCRIPTION  "Index of this table."
        ::= { ipeStsAutoIpEntry 1 }

    ipeStsAutoIpNEAddress OBJECT-TYPE
        SYNTAX       IpAddress
        MAX-ACCESS   not-accessible
        STATUS       current
        DESCRIPTION  "reserved."
        ::= { ipeStsAutoIpEntry 2 }

    ipeStsAutoIpState OBJECT-TYPE
        SYNTAX       Integer32
        MAX-ACCESS   read-only
        STATUS       current
        DESCRIPTION  
            "AutoIP state information.
            Valid Value (1:before setting<initial value>,2:now setting,
            3:automatic setting,4:manual setting)."
        ::= { ipeStsAutoIpEntry 3 }

    ipeStsAutoIpTempAddress OBJECT-TYPE
        SYNTAX       IpAddress
        MAX-ACCESS   read-only
        STATUS       current
        DESCRIPTION  
            "Temporary IP Address of AutoIP setting.
            initial value = 0.0.0.0
            other value = Temporary IP Address
            If AutoIP state information is 3, Temporary IP Address is valid
            value."
        ::= { ipeStsAutoIpEntry 4 }

    ipeAccessGroup OBJECT IDENTIFIER
        ::= { system5 7 }

    ipeAccessTable OBJECT-TYPE
        SYNTAX       SEQUENCE OF IpeAccessEntry
        MAX-ACCESS   not-accessible
        STATUS       current
        DESCRIPTION  "A table of SNMP access information."
        ::= { ipeAccessGroup 1 }

    ipeAccessEntry OBJECT-TYPE
        SYNTAX       IpeAccessEntry
        MAX-ACCESS   not-accessible
        STATUS       current
        DESCRIPTION  
            "A set of SNMP access information.
            All OID don't check that a set value is valid or invalid."
        INDEX        { ipeAccessIndex }
        ::= { ipeAccessTable 1 }

    IpeAccessEntry ::= SEQUENCE {
        ipeAccessIndex        Integer32,
        ipeAccessNEAddress    IpAddress,
        ipeAccessUserName     DisplayString,
        ipeAccessFromAddress  IpAddress,
        ipeAccessType         INTEGER,
        ipeAccessSessionId    Integer32,
        ipeAccessErrorCode    Integer32
    }

    ipeAccessIndex OBJECT-TYPE
        SYNTAX       Integer32 (1..1)
        MAX-ACCESS   not-accessible
        STATUS       current
        DESCRIPTION  "Index of this table."
        ::= { ipeAccessEntry 1 }

    ipeAccessNEAddress OBJECT-TYPE
        SYNTAX       IpAddress
        MAX-ACCESS   not-accessible
        STATUS       current
        DESCRIPTION  "reserved."
        ::= { ipeAccessEntry 2 }

    ipeAccessUserName OBJECT-TYPE
        SYNTAX       DisplayString (SIZE(1..32))
        MAX-ACCESS   read-write
        STATUS       current
        DESCRIPTION  
            "A user name which is used for CTRL-TRAP and logging. 
            When you send SET-Request, it is necessary to SET this OID to 
            first 'variable-bindings' of the SET-Request PDU.
            
            Please use an ASCII code.
            
            The characters which can be used are '-', '_','0'-'9', 'a'-'z'
            and 'A'-'Z'.
            
            When this OID is read, 0x00(null) is returned."
        ::= { ipeAccessEntry 3 }

    ipeAccessFromAddress OBJECT-TYPE
        SYNTAX       IpAddress
        MAX-ACCESS   read-write
        STATUS       current
        DESCRIPTION  
            "A source IP address which is used for CTRL-TRAP and logging. 
            The use is optional.
            
            When this OID is read, 0.0.0.0 is returned."
        ::= { ipeAccessEntry 4 }

    ipeAccessType OBJECT-TYPE
        SYNTAX       INTEGER {
                         invalid(0),
                         nms(1),
                         webLct(2),
                         cli(3),
                         internal(4)
                     }
        MAX-ACCESS   read-write
        STATUS       current
        DESCRIPTION  
            "A type of connection origin.
            The use is optional.
            
            Whne this OID is read, invalid(0) is returned."
        ::= { ipeAccessEntry 5 }

    ipeAccessSessionId OBJECT-TYPE
        SYNTAX       Integer32
        MAX-ACCESS   read-write
        STATUS       current
        DESCRIPTION  
            "A session ID.
            The use is optional.
            
            When this OID is read, 0 is returned."
        ::= { ipeAccessEntry 6 }

    ipeAccessErrorCode OBJECT-TYPE
        SYNTAX       Integer32
        MAX-ACCESS   read-write
        STATUS       current
        DESCRIPTION  "Error Code."
        ::= { ipeAccessEntry 7 }

-----------------------------------------------
-- End User MIB Object Definitions
-----------------------------------------------

END
